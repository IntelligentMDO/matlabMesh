Attribute VB_Name = "DataTrans_FromExcel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'CatiaPara
'*****************************
Function CatiaPara(ByVal ExcelWorkbook As Object, _
                   ByRef SaveDir As String, ByRef Act_Debug As Integer, ByRef Act_Demo As Integer, ByRef Act_SaveStl As Integer, ByRef Act_SaveIgs As Integer)
     
    Dim Data(1, 1 To 5)
    
    For j = 1 To 5
        Data(1, j) = ExcelWorkbook.Sheets("Sheet1").Cells(1, j)
    Next j
    
    
    SaveDir = Data(1, 1)
    Act_Debug = Data(1, 2)
    Act_Demo = Data(1, 3)
    Act_SaveStl = Data(1, 4)
    Act_SaveIgs = Data(1, 5)
    
End Function


'*****************************
'WingPara
'*****************************
Function WingPara(ByVal ExcelWorkbook As Object, _
                  ByRef Num_Section As Integer, ByRef Num_PointPerSpline As Integer, ByRef Index_SurfConnect As Variant, ByRef Mode_GuideLine As Integer, _
                  ByRef MAC_Length As Double, ByRef MAC_x As Double)

    Dim Data(1, 1 To 4)
    
    For j = 1 To 4
        Data(1, j) = ExcelWorkbook.Sheets("Sheet1").Cells(3, j)
    Next j
    
    Num_Section = Data(1, 1)
    Num_PointPerSpline = Data(1, 2)
    Index_SurfConnect = StringToDouble(Data(1, 3))
    Mode_GuideLine = Data(1, 4)
    
    
    For j = 1 To 2
        Data(1, j) = ExcelWorkbook.Sheets("Sheet1").Cells(4, j)
    Next j
    
    MAC_Length = Data(1, 1)
    MAC_x = Data(1, 2)
    
End Function


'*****************************
'PostPara
'*****************************
Function PostPara(ByVal ExcelWorkbook As Object, _
                  ByRef Mode_Post_CFD As Integer, ByRef Diameter_Fillet As Double, _
                  ByRef Rate_Fluid As Double, ByRef Rate_BOI_Fluid_MAC As Double, ByRef Rate_BOI_Fluid_Span As Double, _
                  ByRef ScaleRate As Double, ByRef Index_NonActSection_ICEM As Variant, ByRef Index_Layer2Connect_ICEM As Variant)
    
    Dim Data(1, 1 To 7)
    
    For j = 1 To 7
        Data(1, j) = ExcelWorkbook.Sheets("Sheet1").Cells(6, j)
    Next j
    
    Mode_Post_CFD = Data(1, 1)
    Diameter_Fillet = Data(1, 2)
    Rate_Fluid = Data(1, 3)
    Rate_BOI_Fluid_MAC = StringToDouble(Data(1, 4))(1)
    Rate_BOI_Fluid_Span = StringToDouble(Data(1, 4))(2)
    ScaleRate = Data(1, 5)
    Index_NonActSection_ICEM = StringToDouble(Data(1, 6))
    Index_Layer2Connect_ICEM = StringToDouble(Data(1, 7))
    
End Function


'*****************************
'LeadPoint
'*****************************
Function LeadPoint(ByVal ExcelWorkbook As Object, ByVal Num_Section) As Variant

    Dim Data(1 To MaxNum_Array, 1 To 3)
    
    For i = 1 To Num_Section
        For j = 1 To 3
            nRow = i + 6
            Data(i, j) = ExcelWorkbook.Sheets("Sheet1").Cells(nRow, j)
        Next j
    Next i
    
    
    LeadPoint = Data
    
End Function


'*****************************
'SectionPoint
'*****************************
Function SectionPoint(ByVal ExcelWorkbook As Object, ByVal Num_Section As Integer, ByVal Num_PointPerSpline As Integer) As Variant
    
    Dim Data As Variant
    
    Num_Point = Num_Section * 2 * Num_PointPerSpline
    
    Data = ExcelWorkbook.Sheets("Sheet1").Range("A" & CStr(7 + Num_Section + 1) & ":" & "C" & CStr(7 + Num_Section + Num_Point)).Value
    
    
    SectionPoint = Data
    
End Function

Attribute VB_Name = "DataTrans_ToExcel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'PointCoord
'*****************************
Function PointCoord(ByVal ExcelWorkbook As Object, ByVal DocumentObject As Object, _
                    ByRef Entity_ICEM_Subline_01 As Type_ICEM_Subline_01, _
                    ByRef Entity_ICEM_Subline_12 As Type_ICEM_Subline_12, _
                    ByRef Entity_ICEM_Subline_23 As Type_ICEM_Subline_23, _
                    ByVal Num_Section As Integer, _
                    ByVal Index_NonActSection_ICEM As Variant)
    
    Dim XYZ_Cache(2)
    
    Num_Span_Local = Array(999, 13, 6, 6)
    
    Num_Span = Array(999, Entity_ICEM_Subline_01.Num_Span, Entity_ICEM_Subline_12.Num_Span, Entity_ICEM_Subline_23.Num_Span)

    Num_Divide = Array(999, 11, 11, 11)
    Num_Layer = Array(999, 2, 4, 2)
    
    Num_Tip_x = Array(999, 9, 9, 9)
    Num_Tip_y = Array(999, 3, 3, 3)
    Num_Tip_z = Num_Layer


'-----------------------------------
'Geometry_Post_ICEM_Subline_01
'-----------------------------------
    
    '-----------------------------------
    'Spline_SectionOffset_Point
    '-----------------------------------
    Dim Data_Spline_SectionOffset_Point() As Double
    Dim Data_Write_1() As Double
        
    ReDim Data_Spline_SectionOffset_Point(1 To Num_Span_Local(1), 1 To 2, 1 To Num_Divide(1), 1 To Num_Layer(1), 1 To 3) As Double
    ReDim Data_Write_1(1 To Num_Span_Local(1) * 2 * Num_Divide(1) * Num_Layer(1), 1 To 3) As Double


    'Get Coord
    nSpan_Local = 0
    
    For nSpan = 1 To Num_Span(1)
        
        nSection = Int(nSpan / 3) + 1
                    
        If Not IsInArray(nSection, Index_NonActSection_ICEM) Then
                        
            nSpan_Local = nSpan_Local + 1
                        
            For nDu = 1 To 2
                For nDivide = 1 To Num_Divide(1)
                    For nLayer = 1 To Num_Layer(1)
                        
                        Set Point = Entity_ICEM_Subline_01.Spline_SectionOffset_Point(nSpan, nDu, nDivide, nLayer)
    
                        Point.GetCoordinates XYZ_Cache
    
                        Data_Spline_SectionOffset_Point(nSpan_Local, nDu, nDivide, nLayer, 1) = XYZ_Cache(0)
                        Data_Spline_SectionOffset_Point(nSpan_Local, nDu, nDivide, nLayer, 2) = XYZ_Cache(1)
                        Data_Spline_SectionOffset_Point(nSpan_Local, nDu, nDivide, nLayer, 3) = XYZ_Cache(2)
                            
                    Next nLayer
                Next nDivide
            Next nDu
            
        End If
            
    Next nSpan
    

    'Write
    nSpan_Local = 0
    nPoint = 0

    For nSpan = 1 To Num_Span(1)
    
        nSection = Int(nSpan / 3) + 1
                    
        If Not IsInArray(nSection, Index_NonActSection_ICEM) Then
                        
            nSpan_Local = nSpan_Local + 1
                        
            For nDu = 1 To 2
                For nDivide = 1 To Num_Divide(1)
                    For nLayer = 1 To Num_Layer(1)
                        
                        nPoint = nPoint + 1
    
                        Data_Write_1(nPoint, 1) = Data_Spline_SectionOffset_Point(nSpan_Local, nDu, nDivide, nLayer, 1)
                        Data_Write_1(nPoint, 2) = Data_Spline_SectionOffset_Point(nSpan_Local, nDu, nDivide, nLayer, 2)
                        Data_Write_1(nPoint, 3) = Data_Spline_SectionOffset_Point(nSpan_Local, nDu, nDivide, nLayer, 3)
   
                    Next nLayer
                Next nDivide
            Next nDu
        
        End If
        
    Next nSpan
    
    
    Row_Init = 6 + Num_Section + 2
    Row_End = Row_Init + (Num_Span_Local(1) * 2 * Num_Divide(1) * Num_Layer(1) - 1)
    
    ExcelWorkbook.Sheets("Sheet1").Range("E" & CStr(Row_Init) & ":" & "G" & CStr(Row_End)).Value = Data_Write_1


    '-----------------------------------
    'Spline_SectionOffset_Tip_Point
    '-----------------------------------
    Dim Data_Spline_SectionOffset_Tip_Point() As Double
    Dim Data_Write_2() As Double
        
    ReDim Data_Spline_SectionOffset_Tip_Point(1 To Num_Tip_x(1), 1 To Num_Tip_y(1), 1 To Num_Tip_z(1), 1 To 3) As Double
    ReDim Data_Write_2(1 To Num_Tip_x(1) * Num_Tip_y(1) * Num_Tip_z(1), 1 To 3) As Double
    
    
    'Get Coord
    For nTip_x = 1 To Num_Tip_x(1)
        For nTip_y = 1 To Num_Tip_y(1)
            For nTip_z = 1 To Num_Tip_z(1)
                
                If nTip_y = 1 Then
                    
                    Set Point = Entity_ICEM_Subline_01.Spline_SectionOffset_Point(Num_Span(1), 1, nTip_x + 1, nTip_z)
                    
                ElseIf nTip_y = 2 Then
                    
                    If nTip_x = 1 Then
                    
                        Set Point = Entity_ICEM_Subline_01.Spline_SectionOffset_Point(Num_Span(1), 1, 1, nTip_z)
                        
                    ElseIf nTip_x > 1 And nTip_x < Num_Tip_x(1) Then
                    
                        Set Point = Entity_ICEM_Subline_01.Spline_SectionOffset_Tip_Point(nTip_x - 1, nTip_z)
                    
                    ElseIf nTip_x = Num_Tip_x(1) Then
                    
                        Set Point = Entity_ICEM_Subline_01.Spline_SectionOffset_Point(Num_Span(1), 1, Num_Divide(1), nTip_z)
                        
                    End If
                
                ElseIf nTip_y = 3 Then
                
                    Set Point = Entity_ICEM_Subline_01.Spline_SectionOffset_Point(Num_Span(1), 2, nTip_x + 1, nTip_z)
                
                End If
    
                Set M = DocumentObject.GetWorkbench("SPAWorkbench").GetMeasurable(Point)
                M.GetPoint XYZ_Cache
    
                Data_Spline_SectionOffset_Tip_Point(nTip_x, nTip_y, nTip_z, 1) = XYZ_Cache(0)
                Data_Spline_SectionOffset_Tip_Point(nTip_x, nTip_y, nTip_z, 2) = XYZ_Cache(1)
                Data_Spline_SectionOffset_Tip_Point(nTip_x, nTip_y, nTip_z, 3) = XYZ_Cache(2)
            
            Next nTip_z
        Next nTip_y
    Next nTip_x
    
    
    'Write
    nPoint = 0

    For nTip_x = 1 To Num_Tip_x(1)
        For nTip_y = 1 To Num_Tip_y(1)
            For nTip_z = 1 To Num_Tip_z(1)

                nPoint = nPoint + 1
    
                Data_Write_2(nPoint, 1) = Data_Spline_SectionOffset_Tip_Point(nTip_x, nTip_y, nTip_z, 1)
                Data_Write_2(nPoint, 2) = Data_Spline_SectionOffset_Tip_Point(nTip_x, nTip_y, nTip_z, 2)
                Data_Write_2(nPoint, 3) = Data_Spline_SectionOffset_Tip_Point(nTip_x, nTip_y, nTip_z, 3)

            Next nTip_z
        Next nTip_y
    Next nTip_x
    
    
    Row_Init = Row_End + 2
    Row_End = Row_Init + (Num_Tip_x(1) * Num_Tip_y(1) * Num_Tip_z(1) - 1)
    
    ExcelWorkbook.Sheets("Sheet1").Range("E" & CStr(Row_Init) & ":" & "G" & CStr(Row_End)).Value = Data_Write_2
    
    
'-----------------------------------
'Geometry_Post_ICEM_Subline_12
'-----------------------------------
    
    '-----------------------------------
    'Spline_Tran_z_Point_Reduce
    '-----------------------------------
    Dim Data_Spline_Tran_z_Point_Reduce() As Double
    Dim Data_Write_3() As Double

    ReDim Data_Spline_Tran_z_Point_Reduce(1 To Num_Span_Local(2), 1 To 2, 1 To Num_Divide(2), 1 To Num_Layer(2), 1 To 3) As Double
    ReDim Data_Write_3(1 To Num_Span_Local(2) * 2 * Num_Divide(2) * Num_Layer(2), 1 To 3) As Double


    'Get Coord
    nSpan_Local = 0
     
    For nSpan = 1 To Num_Span(2)
    
        nSection = Int(Entity_ICEM_Subline_12.Span(nSpan) / 3) + 1
                    
        If Not IsInArray(nSection, Index_NonActSection_ICEM) Then
                        
            nSpan_Local = nSpan_Local + 1
            
            For nDu = 1 To 2
                For nDivide = 1 To Num_Divide(2)
                    For nLayer = 1 To Num_Layer(2)
    
                        Set Point = Entity_ICEM_Subline_12.Spline_Tran_z_Point_Reduce(nSpan, nDu, nDivide, nLayer)
    
                        Set M = DocumentObject.GetWorkbench("SPAWorkbench").GetMeasurable(Point)
                        M.GetPoint XYZ_Cache
    
                        Data_Spline_Tran_z_Point_Reduce(nSpan_Local, nDu, nDivide, nLayer, 1) = XYZ_Cache(0)
                        Data_Spline_Tran_z_Point_Reduce(nSpan_Local, nDu, nDivide, nLayer, 2) = XYZ_Cache(1)
                        Data_Spline_Tran_z_Point_Reduce(nSpan_Local, nDu, nDivide, nLayer, 3) = XYZ_Cache(2)
    
    
                    Next nLayer
                Next nDivide
            Next nDu
            
        End If
        
    Next nSpan


    'Write
    nSpan_Local = 0
    nPoint = 0

    For nSpan = 1 To Num_Span(2)
    
        nSection = Int(Entity_ICEM_Subline_12.Span(nSpan) / 3) + 1
                    
        If Not IsInArray(nSection, Index_NonActSection_ICEM) Then
                        
            nSpan_Local = nSpan_Local + 1
            
            For nDu = 1 To 2
                For nDivide = 1 To Num_Divide(2)
                    For nLayer = 1 To Num_Layer(2)
    
                        nPoint = nPoint + 1
    
                        Data_Write_3(nPoint, 1) = Data_Spline_Tran_z_Point_Reduce(nSpan_Local, nDu, nDivide, nLayer, 1)
                        Data_Write_3(nPoint, 2) = Data_Spline_Tran_z_Point_Reduce(nSpan_Local, nDu, nDivide, nLayer, 2)
                        Data_Write_3(nPoint, 3) = Data_Spline_Tran_z_Point_Reduce(nSpan_Local, nDu, nDivide, nLayer, 3)
    
                    Next nLayer
                Next nDivide
            Next nDu
        
        End If
        
    Next nSpan


    Row_Init = 6 + Num_Section + 2
    Row_End = Row_Init + (Num_Span_Local(2) * 2 * Num_Divide(2) * Num_Layer(2) - 1)

    ExcelWorkbook.Sheets("Sheet1").Range("I" & CStr(Row_Init) & ":" & "K" & CStr(Row_End)).Value = Data_Write_3


    '-----------------------------------
    'Spline_Tran_Tip_Point_Reduce
    '-----------------------------------
    Dim Data_Spline_Tran_Tip_Point_Reduce() As Double
    Dim Data_Write_4() As Double
        
    ReDim Data_Spline_Tran_Tip_Point_Reduce(1 To Num_Tip_x(2), 1 To Num_Tip_y(2), 1 To Num_Tip_z(2), 1 To 3) As Double
    ReDim Data_Write_4(1 To Num_Tip_x(2) * Num_Tip_y(2) * Num_Tip_z(2), 1 To 3) As Double
    
    
    'Get Coord
    For nTip_x = 1 To Num_Tip_x(2)
        For nTip_y = 1 To Num_Tip_y(2)
            For nTip_z = 1 To Num_Tip_z(2)
                
                If nTip_y = 1 Then
                    
                    Set Point = Entity_ICEM_Subline_12.Spline_Tran_z_Point_Reduce(Num_Span(2), 1, nTip_x + 1, nTip_z)
                    
                ElseIf nTip_y = 2 Then
                    
                    If nTip_x = 1 Then
                    
                        Set Point = Entity_ICEM_Subline_12.Spline_Tran_z_Point_Reduce(Num_Span(2), 1, 1, nTip_z)
                        
                    ElseIf nTip_x > 1 And nTip_x < Num_Tip_x(2) Then
                    
                        Set Point = Entity_ICEM_Subline_12.Spline_Tran_Tip_Point_Reduce(nTip_x - 1, nTip_z)
                    
                    ElseIf nTip_x = Num_Tip_x(2) Then
                    
                        Set Point = Entity_ICEM_Subline_12.Spline_Tran_z_Point_Reduce(Num_Span(2), 1, Num_Divide(2), nTip_z)
                        
                    End If
                
                ElseIf nTip_y = 3 Then
                
                    Set Point = Entity_ICEM_Subline_12.Spline_Tran_z_Point_Reduce(Num_Span(2), 2, nTip_x + 1, nTip_z)
                
                End If
    
                Set M = DocumentObject.GetWorkbench("SPAWorkbench").GetMeasurable(Point)
                M.GetPoint XYZ_Cache
    
                Data_Spline_Tran_Tip_Point_Reduce(nTip_x, nTip_y, nTip_z, 1) = XYZ_Cache(0)
                Data_Spline_Tran_Tip_Point_Reduce(nTip_x, nTip_y, nTip_z, 2) = XYZ_Cache(1)
                Data_Spline_Tran_Tip_Point_Reduce(nTip_x, nTip_y, nTip_z, 3) = XYZ_Cache(2)
            
            Next nTip_z
        Next nTip_y
    Next nTip_x


    'Write
    nPoint = 0

    For nTip_x = 1 To Num_Tip_x(2)
        For nTip_y = 1 To Num_Tip_y(2)
            For nTip_z = 1 To Num_Tip_z(2)

                nPoint = nPoint + 1
    
                Data_Write_4(nPoint, 1) = Data_Spline_Tran_Tip_Point_Reduce(nTip_x, nTip_y, nTip_z, 1)
                Data_Write_4(nPoint, 2) = Data_Spline_Tran_Tip_Point_Reduce(nTip_x, nTip_y, nTip_z, 2)
                Data_Write_4(nPoint, 3) = Data_Spline_Tran_Tip_Point_Reduce(nTip_x, nTip_y, nTip_z, 3)

            Next nTip_z
        Next nTip_y
    Next nTip_x
    
    
    Row_Init = Row_End + 2
    Row_End = Row_Init + (Num_Tip_x(2) * Num_Tip_y(2) * Num_Tip_z(2) - 1)

    ExcelWorkbook.Sheets("Sheet1").Range("I" & CStr(Row_Init) & ":" & "K" & CStr(Row_End)).Value = Data_Write_4
    

'-----------------------------------
'Geometry_Post_ICEM_Subline_23
'-----------------------------------

    '-----------------------------------
    'Spline_Tran_z_Point
    '-----------------------------------
    Dim Data_Spline_Tran_z_Point() As Double
    Dim Data_Write_5() As Double
     
    ReDim Data_Spline_Tran_z_Point(1 To Num_Span_Local(3), 1 To 2, 1 To Num_Divide(3), 1 To Num_Layer(3), 1 To 3) As Double
    ReDim Data_Write_5(1 To Num_Span_Local(3) * 2 * Num_Divide(3) * Num_Layer(3), 1 To 3) As Double


    'Get Coord
    nSpan_Local = 0
    
    For nSpan = 1 To Num_Span(3)
    
        nSection = Int(Entity_ICEM_Subline_23.Span(nSpan) / 3) + 1
                    
        If Not IsInArray(nSection, Index_NonActSection_ICEM) Then
                            
            nSpan_Local = nSpan_Local + 1
            
            For nDu = 1 To 2
                For nDivide = 1 To Num_Divide(3)
                    For nLayer = 1 To Num_Layer(3)
                    
                        Set Point = Entity_ICEM_Subline_23.Spline_Tran_z_Point(nSpan, nDu, nDivide, nLayer)
    
                        Set M = DocumentObject.GetWorkbench("SPAWorkbench").GetMeasurable(Point)
                        M.GetPoint XYZ_Cache
            
                        Data_Spline_Tran_z_Point(nSpan_Local, nDu, nDivide, nLayer, 1) = XYZ_Cache(0)
                        Data_Spline_Tran_z_Point(nSpan_Local, nDu, nDivide, nLayer, 2) = XYZ_Cache(1)
                        Data_Spline_Tran_z_Point(nSpan_Local, nDu, nDivide, nLayer, 3) = XYZ_Cache(2)
                    
                    Next nLayer
                Next nDivide
            Next nDu
        
        End If
        
    Next nSpan
    
    
    'Write
    nSpan_Local = 0
    nPoint = 0

    For nSpan = 1 To Num_Span(3)
    
        nSection = Int(Entity_ICEM_Subline_23.Span(nSpan) / 3) + 1
                    
        If Not IsInArray(nSection, Index_NonActSection_ICEM) Then
                            
            nSpan_Local = nSpan_Local + 1
            
            For nDu = 1 To 2
                For nDivide = 1 To Num_Divide(3)
                    For nLayer = 1 To Num_Layer(3)
    
                        nPoint = nPoint + 1
            
                        Data_Write_5(nPoint, 1) = Data_Spline_Tran_z_Point(nSpan_Local, nDu, nDivide, nLayer, 1)
                        Data_Write_5(nPoint, 2) = Data_Spline_Tran_z_Point(nSpan_Local, nDu, nDivide, nLayer, 2)
                        Data_Write_5(nPoint, 3) = Data_Spline_Tran_z_Point(nSpan_Local, nDu, nDivide, nLayer, 3)
                        
                    Next nLayer
                Next nDivide
            Next nDu
        
        End If
        
    Next nSpan
    
    
    Row_Init = 6 + Num_Section + 2
    Row_End = Row_Init + (Num_Span_Local(3) * 2 * Num_Divide(3) * Num_Layer(3) - 1)
    
    ExcelWorkbook.Sheets("Sheet1").Range("M" & CStr(Row_Init) & ":" & "O" & CStr(Row_End)).Value = Data_Write_5
    
    
    '-----------------------------------
    'Spline_Tran_Tip_Point
    '-----------------------------------
    Dim Data_Spline_Tran_Tip_Point() As Double
    Dim Data_Write_6() As Double
        
    ReDim Data_Spline_Tran_Tip_Point(1 To Num_Tip_x(3), 1 To Num_Tip_y(3), 1 To Num_Tip_z(3), 1 To 3) As Double
    ReDim Data_Write_6(1 To Num_Tip_x(3) * Num_Tip_y(3) * Num_Tip_z(3), 1 To 3) As Double
    
    
    'Get Coord
    For nTip_x = 1 To Num_Tip_x(3)
        For nTip_y = 1 To Num_Tip_y(3)
            For nTip_z = 1 To Num_Tip_z(3)
                
                If nTip_y = 1 Then
                    
                    Set Point = Entity_ICEM_Subline_23.Spline_Tran_z_Point(Num_Span(3), 1, nTip_x + 1, nTip_z)
                    
                ElseIf nTip_y = 2 Then
                    
                    If nTip_x = 1 Then
                    
                        Set Point = Entity_ICEM_Subline_23.Spline_Tran_z_Point(Num_Span(3), 1, 1, nTip_z)
                        
                    ElseIf nTip_x > 1 And nTip_x < Num_Tip_x(3) Then
                    
                        Set Point = Entity_ICEM_Subline_23.Spline_Tran_Tip_Point(nTip_x - 1, nTip_z)
                    
                    ElseIf nTip_x = Num_Tip_x(3) Then
                    
                        Set Point = Entity_ICEM_Subline_23.Spline_Tran_z_Point(Num_Span(3), 1, Num_Divide(3), nTip_z)
                        
                    End If
                
                ElseIf nTip_y = 3 Then
                
                    Set Point = Entity_ICEM_Subline_23.Spline_Tran_z_Point(Num_Span(3), 2, nTip_x + 1, nTip_z)
                
                End If
    
                Set M = DocumentObject.GetWorkbench("SPAWorkbench").GetMeasurable(Point)
                M.GetPoint XYZ_Cache
    
                Data_Spline_Tran_Tip_Point(nTip_x, nTip_y, nTip_z, 1) = XYZ_Cache(0)
                Data_Spline_Tran_Tip_Point(nTip_x, nTip_y, nTip_z, 2) = XYZ_Cache(1)
                Data_Spline_Tran_Tip_Point(nTip_x, nTip_y, nTip_z, 3) = XYZ_Cache(2)
            
            Next nTip_z
        Next nTip_y
    Next nTip_x


    'Write
    nPoint = 0

    For nTip_x = 1 To Num_Tip_x(3)
        For nTip_y = 1 To Num_Tip_y(3)
            For nTip_z = 1 To Num_Tip_z(3)

                nPoint = nPoint + 1
    
                Data_Write_6(nPoint, 1) = Data_Spline_Tran_Tip_Point(nTip_x, nTip_y, nTip_z, 1)
                Data_Write_6(nPoint, 2) = Data_Spline_Tran_Tip_Point(nTip_x, nTip_y, nTip_z, 2)
                Data_Write_6(nPoint, 3) = Data_Spline_Tran_Tip_Point(nTip_x, nTip_y, nTip_z, 3)

            Next nTip_z
        Next nTip_y
    Next nTip_x
    
    
    Row_Init = Row_End + 2
    Row_End = Row_Init + (Num_Tip_x(3) * Num_Tip_y(3) * Num_Tip_z(3) - 1)
    
    ExcelWorkbook.Sheets("Sheet1").Range("M" & CStr(Row_Init) & ":" & "O" & CStr(Row_End)).Value = Data_Write_6
    
End Function

Attribute VB_Name = "Export"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
    
    
'*****************************
'Baisc
'*****************************
Function Basic(ByVal DocumentObject As Object, ByVal SaveDir As String, ByVal Act_SaveStl As Integer, ByVal Act_SaveIgs As Integer, ByVal Zoom_Local_1 As Double)
     
    '-----------------------------------
    'Export .CATPart
    '-----------------------------------
    If Err.Number <> 0 Then
    
        SaveDir_CATPart = SaveDir & ".CATPart.Error"
        
        DocumentObject.SaveAs SaveDir_CATPart
        
    Else
        
        DocumentObject.Part.InWorkObject = DocumentObject.Part.OrderedGeometricalSets.Item("PLANE")
        
        
        DocumentObject.Selection.Add DocumentObject.Part.OrderedGeometricalSets.Item("PLANE")
        DocumentObject.Selection.Add DocumentObject.Part.OrderedGeometricalSets.Item("PLANE").HybridShapes.Item("SectionShape")
    
        DocumentObject.Selection.VisProperties.SetShow 0
        DocumentObject.Selection.Clear
        
        
        Set View = CATIA.ActiveWindow.ActiveViewer
        Set ViewPoint = View.Viewpoint3D
        ViewPoint.Zoom = Zoom_Local_1
        View.Update
        
        
        SaveDir_CATPart = SaveDir & ".CATPart"
    
        'If Dir(SaveDir_CATPart) <> "" Then
        '    Kill SaveDir_CATPart
        'End If
    
        DocumentObject.SaveAs SaveDir_CATPart
        
        
        DocumentObject.Selection.Add DocumentObject.Part.OrderedGeometricalSets.Item("PLANE").HybridShapes.Item("SectionShape")
    
        DocumentObject.Selection.VisProperties.SetShow 1
        DocumentObject.Selection.Clear
    
    End If
    
    
    '-----------------------------------
    'Export .stl
    '-----------------------------------
    If Err.Number = 0 And Act_SaveStl = 1 Then

        SaveDir_Stl = SaveDir & ".stl"
        
        If Dir(SaveDir_Stl) <> "" Then
            Kill SaveDir_Stl
        End If

        DocumentObject.ExportData SaveDir_Stl, "stl"

    End If
    
    
    '-----------------------------------
    'Export .igs
    '-----------------------------------
    If Err.Number = 0 And Act_SaveIgs = 1 Then
                
        SaveDir_Igs = SaveDir & ".igs"
        
        If Dir(SaveDir_Igs) <> "" Then
            Kill SaveDir_Igs
        End If

        DocumentObject.ExportData SaveDir_Igs, "igs"

    End If
     
End Function


'*****************************
'ICEM
'*****************************
Function ICEM(ByVal DocumentObject As Object, ByVal SaveDir As String, _
              ByVal Act_SaveStl As Integer, ByVal Act_SaveIgs As Integer, ByVal Zoom_Local_1 As Double, _
              ByVal ScaleRate As Double, ByRef Entity_ICEM_FluidAndBOI As Type_ICEM_FluidAndBOI, _
              ByRef Entity_ICEM_Subline_01 As Type_ICEM_Subline_01, ByRef Entity_ICEM_Subline_12 As Type_ICEM_Subline_12, ByRef Entity_ICEM_Subline_23 As Type_ICEM_Subline_23)
        
    '-----------------------------------
    'Export .CATPart
    '-----------------------------------
    If Err.Number <> 0 Then
    
        SaveDir_CATPart = SaveDir & ".CATPart.Error"
        
        DocumentObject.SaveAs SaveDir_CATPart
        
    Else
        
        DocumentObject.Part.InWorkObject = DocumentObject.Part.OrderedGeometricalSets.Item("PLANE")
        
        
        DocumentObject.Selection.Add DocumentObject.Part.OrderedGeometricalSets.Item("PLANE")
        DocumentObject.Selection.Add DocumentObject.Part.OrderedGeometricalSets.Item("PLANE").HybridShapes.Item("SectionShape")
    
        DocumentObject.Selection.VisProperties.SetShow 0
        DocumentObject.Selection.Clear
        
        DocumentObject.Selection.Add DocumentObject.Part.OrderedGeometricalSets.Item("BOI_FLUID")
        DocumentObject.Selection.Add DocumentObject.Part.OrderedGeometricalSets.Item("IN")
        DocumentObject.Selection.Add DocumentObject.Part.OrderedGeometricalSets.Item("SYMM")
        DocumentObject.Selection.Add DocumentObject.Part.OrderedGeometricalSets.Item("ICEM_Subline_01")
        DocumentObject.Selection.Add DocumentObject.Part.OrderedGeometricalSets.Item("ICEM_Subline_12")
        DocumentObject.Selection.Add DocumentObject.Part.OrderedGeometricalSets.Item("ICEM_Subline_23")
    
        DocumentObject.Selection.VisProperties.SetShow 1
        DocumentObject.Selection.Clear
    
        
        Set View = CATIA.ActiveWindow.ActiveViewer
        Set ViewPoint = View.Viewpoint3D
        ViewPoint.Zoom = Zoom_Local_1
        View.Update
        
    
        SaveDir_CATPart = SaveDir & ".CATPart"
    
        'If Dir(SaveDir_CATPart) <> "" Then
        '    Kill SaveDir_CATPart
        'End If
    
        DocumentObject.SaveAs SaveDir_CATPart
        
        
        DocumentObject.Selection.Add DocumentObject.Part.OrderedGeometricalSets.Item("PLANE").HybridShapes.Item("SectionShape")
    
        DocumentObject.Selection.VisProperties.SetShow 1
        DocumentObject.Selection.Clear
        
        
    End If
    
    
    '-----------------------------------
    'Export .stl
    '-----------------------------------
    If Err.Number = 0 And Act_SaveStl = 1 Then

        SaveDir_Stl = SaveDir & ".stl"

        If Dir(SaveDir_Stl) <> "" Then
            Kill SaveDir_Stl
        End If

        DocumentObject.ExportData SaveDir_Stl, "stl"

    End If
    
    
    '-----------------------------------
    'Export .igs
    '-----------------------------------
    If Err.Number = 0 And Act_SaveIgs = 1 Then
                
        SaveDir_Igs = SaveDir & ".igs"
        
        If Dir(SaveDir_Igs) <> "" Then
            Kill SaveDir_Igs
        End If

        DocumentObject.ExportData SaveDir_Igs, "igs"

    End If


    '-----------------------------------
    'Export .model
    '-----------------------------------
    'Scale
    If Err.Number = 0 Then
    
        Set WorkObject = DocumentObject.Part.OrderedGeometricalSets.Add()
        DocumentObject.Part.OrderedGeometricalSets.Item(8).Name = "Scale"
        
        Set DPH = DocumentObject.Part.HybridShapeFactory
        
        
        Set Point_Ref = DPH.AddNewPointCoord(0, 0, 0)
        
        
        Set Scale_BOI_FLUID_Surface_BOI_Fluid = DPH.AddNewHybridScaling(Entity_ICEM_FluidAndBOI.Extract_Surface_BOI_Fluid, Point_Ref, ScaleRate)
        Set Scale_IN_Surface_Fluid = DPH.AddNewHybridScaling(Entity_ICEM_FluidAndBOI.Extract_Surface_Fluid, Point_Ref, ScaleRate)
        Set Scale_SYMM_Surface_Symm = DPH.AddNewHybridScaling(Entity_ICEM_FluidAndBOI.Extract_Surface_Symm, Point_Ref, ScaleRate)
        
        WorkObject.InsertHybridShape Scale_BOI_FLUID_Surface_BOI_Fluid
        WorkObject.InsertHybridShape Scale_IN_Surface_Fluid
        WorkObject.InsertHybridShape Scale_SYMM_Surface_Symm
        
        Scale_BOI_FLUID_Surface_BOI_Fluid.Name = "Scale_BOI_FLUID_Surface_BOI_Fluid"
        Scale_IN_Surface_Fluid.Name = "Scale_IN_Surface_Fluid"
        Scale_SYMM_Surface_Symm.Name = "Scale_SYMM_Surface_Symm"
        
        
        Set Scale_ICEM_Subline_12_Spline_Tran_z_Point_Reduce = DPH.AddNewHybridScaling(Entity_ICEM_Subline_12.Extract_Spline_Tran_z_Point_Reduce, Point_Ref, ScaleRate)
        Set Scale_ICEM_Subline_12_Spline_Tran_Tip_Point_Reduce = DPH.AddNewHybridScaling(Entity_ICEM_Subline_12.Extract_Spline_Tran_Tip_Point_Reduce, Point_Ref, ScaleRate)
        Set Scale_ICEM_Subline_12_Spline_Tran_x_Reduce = DPH.AddNewHybridScaling(Entity_ICEM_Subline_12.Extract_Spline_Tran_x_Reduce, Point_Ref, ScaleRate)
        Set Scale_ICEM_Subline_12_Spline_Tran_y_Reduce = DPH.AddNewHybridScaling(Entity_ICEM_Subline_12.Extract_Spline_Tran_y_Reduce, Point_Ref, ScaleRate)
        Set Scale_ICEM_Subline_12_Spline_Tran_z = DPH.AddNewHybridScaling(Entity_ICEM_Subline_12.Extract_Spline_Tran_z, Point_Ref, ScaleRate)
        Set Scale_ICEM_Subline_12_Spline_Tran_Tip_xyz = DPH.AddNewHybridScaling(Entity_ICEM_Subline_12.Extract_Spline_Tran_Tip_xyz, Point_Ref, ScaleRate)
        
        WorkObject.InsertHybridShape Scale_ICEM_Subline_12_Spline_Tran_z_Point_Reduce
        WorkObject.InsertHybridShape Scale_ICEM_Subline_12_Spline_Tran_Tip_Point_Reduce
        WorkObject.InsertHybridShape Scale_ICEM_Subline_12_Spline_Tran_x_Reduce
        WorkObject.InsertHybridShape Scale_ICEM_Subline_12_Spline_Tran_y_Reduce
        WorkObject.InsertHybridShape Scale_ICEM_Subline_12_Spline_Tran_z
        WorkObject.InsertHybridShape Scale_ICEM_Subline_12_Spline_Tran_Tip_xyz
    
        Scale_ICEM_Subline_12_Spline_Tran_z_Point_Reduce.Name = "Scale_ICEM_Subline_12_Spline_Tran_z_Point_Reduce"
        Scale_ICEM_Subline_12_Spline_Tran_Tip_Point_Reduce.Name = "Scale_ICEM_Subline_12_Spline_Tran_Tip_Point_Reduce"
        Scale_ICEM_Subline_12_Spline_Tran_x_Reduce.Name = "Scale_ICEM_Subline_12_Spline_Tran_x_Reduce"
        Scale_ICEM_Subline_12_Spline_Tran_y_Reduce.Name = "Scale_ICEM_Subline_12_Spline_Tran_y_Reduce"
        Scale_ICEM_Subline_12_Spline_Tran_z.Name = "Scale_ICEM_Subline_12_Spline_Tran_z"
        Scale_ICEM_Subline_12_Spline_Tran_Tip_xyz.Name = "Scale_ICEM_Subline_12_Spline_Tran_Tip_xyz"
        
        
        Set Scale_ICEM_Subline_23_Spline_Tran_z_Point = DPH.AddNewHybridScaling(Entity_ICEM_Subline_23.Extract_Spline_Tran_z_Point, Point_Ref, ScaleRate)
        Set Scale_ICEM_Subline_23_Spline_Tran_Tip_Point = DPH.AddNewHybridScaling(Entity_ICEM_Subline_23.Extract_Spline_Tran_Tip_Point, Point_Ref, ScaleRate)
        Set Scale_ICEM_Subline_23_Spline_Tran_x = DPH.AddNewHybridScaling(Entity_ICEM_Subline_23.Extract_Spline_Tran_x, Point_Ref, ScaleRate)
        Set Scale_ICEM_Subline_23_Spline_Tran_y = DPH.AddNewHybridScaling(Entity_ICEM_Subline_23.Extract_Spline_Tran_y, Point_Ref, ScaleRate)
        Set Scale_ICEM_Subline_23_Spline_Tran_z = DPH.AddNewHybridScaling(Entity_ICEM_Subline_23.Extract_Spline_Tran_z, Point_Ref, ScaleRate)
        Set Scale_ICEM_Subline_23_Spline_Tran_Tip_xyz = DPH.AddNewHybridScaling(Entity_ICEM_Subline_23.Extract_Spline_Tran_Tip_xyz, Point_Ref, ScaleRate)
        
        WorkObject.InsertHybridShape Scale_ICEM_Subline_23_Spline_Tran_z_Point
        WorkObject.InsertHybridShape Scale_ICEM_Subline_23_Spline_Tran_Tip_Point
        WorkObject.InsertHybridShape Scale_ICEM_Subline_23_Spline_Tran_x
        WorkObject.InsertHybridShape Scale_ICEM_Subline_23_Spline_Tran_y
        WorkObject.InsertHybridShape Scale_ICEM_Subline_23_Spline_Tran_z
        WorkObject.InsertHybridShape Scale_ICEM_Subline_23_Spline_Tran_Tip_xyz
    
        Scale_ICEM_Subline_23_Spline_Tran_z_Point.Name = "Scale_ICEM_Subline_23_Spline_Tran_z_Point"
        Scale_ICEM_Subline_23_Spline_Tran_Tip_Point.Name = "Scale_ICEM_Subline_23_Spline_Tran_Tip_Point"
        Scale_ICEM_Subline_23_Spline_Tran_x.Name = "Scale_ICEM_Subline_23_Spline_Tran_x"
        Scale_ICEM_Subline_23_Spline_Tran_y.Name = "Scale_ICEM_Subline_23_Spline_Tran_y"
        Scale_ICEM_Subline_23_Spline_Tran_z.Name = "Scale_ICEM_Subline_23_Spline_Tran_z"
        Scale_ICEM_Subline_23_Spline_Tran_Tip_xyz.Name = "Scale_ICEM_Subline_23_Spline_Tran_Tip_xyz"
        
        
        DocumentObject.Selection.Add Scale_BOI_FLUID_Surface_BOI_Fluid
        DocumentObject.Selection.Add Scale_IN_Surface_Fluid
        DocumentObject.Selection.Add Scale_SYMM_Surface_Symm
        
        DocumentObject.Selection.Add Scale_ICEM_Subline_12_Spline_Tran_z_Point_Reduce
        DocumentObject.Selection.Add Scale_ICEM_Subline_12_Spline_Tran_Tip_Point_Reduce
        DocumentObject.Selection.Add Scale_ICEM_Subline_12_Spline_Tran_x_Reduce
        DocumentObject.Selection.Add Scale_ICEM_Subline_12_Spline_Tran_y_Reduce
        DocumentObject.Selection.Add Scale_ICEM_Subline_12_Spline_Tran_z
        DocumentObject.Selection.Add Scale_ICEM_Subline_12_Spline_Tran_Tip_xyz
        
        DocumentObject.Selection.Add Scale_ICEM_Subline_23_Spline_Tran_z_Point
        DocumentObject.Selection.Add Scale_ICEM_Subline_23_Spline_Tran_Tip_Point
        DocumentObject.Selection.Add Scale_ICEM_Subline_23_Spline_Tran_x
        DocumentObject.Selection.Add Scale_ICEM_Subline_23_Spline_Tran_y
        DocumentObject.Selection.Add Scale_ICEM_Subline_23_Spline_Tran_z
        DocumentObject.Selection.Add Scale_ICEM_Subline_23_Spline_Tran_Tip_xyz
    
        DocumentObject.Selection.VisProperties.SetShow 1
        DocumentObject.Selection.Clear
        
        
        DocumentObject.Selection.Add DocumentObject.Part.OrderedGeometricalSets.Item("PLANE")
    
        DocumentObject.Selection.VisProperties.SetShow 1
        DocumentObject.Selection.Clear
        
    End If
    
           
    'PLANE
    If Err.Number = 0 Then

        DocumentObject.Selection.Add DocumentObject.Part.OrderedGeometricalSets.Item("PLANE")
        DocumentObject.Selection.VisProperties.SetShow 0
        
        
        SaveDir_PLANE = SaveDir & "_PLANE.model"
        
        If Dir(SaveDir_PLANE) <> "" Then
            Kill SaveDir_PLANE
        End If
        
        DocumentObject.ExportData SaveDir_PLANE, "model"
        
        
        DocumentObject.Selection.VisProperties.SetShow 1
        DocumentObject.Selection.Clear

    End If


    'BOI_FLUID
    If Err.Number = 0 Then

        DocumentObject.Selection.Add Scale_BOI_FLUID_Surface_BOI_Fluid
        DocumentObject.Selection.VisProperties.SetShow 0
        
        
        SaveDir_BOI_FLUID = SaveDir & "_BOI_FLUID.model"

        If Dir(SaveDir_BOI_FLUID) <> "" Then
            Kill SaveDir_BOI_FLUID
        End If

        DocumentObject.ExportData SaveDir_BOI_FLUID, "model"
        
        
        DocumentObject.Selection.VisProperties.SetShow 1
        DocumentObject.Selection.Clear

    End If


    'IN
    If Err.Number = 0 Then

        DocumentObject.Selection.Add Scale_IN_Surface_Fluid
        DocumentObject.Selection.VisProperties.SetShow 0
        
        
        SaveDir_IN = SaveDir & "_IN.model"

        If Dir(SaveDir_IN) <> "" Then
            Kill SaveDir_IN
        End If

        DocumentObject.ExportData SaveDir_IN, "model"
        
        
        DocumentObject.Selection.VisProperties.SetShow 1
        DocumentObject.Selection.Clear

    End If


    'SYMM
    If Err.Number = 0 Then

        DocumentObject.Selection.Add Scale_SYMM_Surface_Symm
        DocumentObject.Selection.VisProperties.SetShow 0
        
        
        SaveDir_SYMM = SaveDir & "_SYMM.model"

        If Dir(SaveDir_SYMM) <> "" Then
            Kill SaveDir_SYMM
        End If

        DocumentObject.ExportData SaveDir_SYMM, "model"
        
        
        DocumentObject.Selection.VisProperties.SetShow 1
        DocumentObject.Selection.Clear

    End If


    'Subline_01
    If Err.Number = 0 Then

        DocumentObject.Selection.Add DocumentObject.Part.OrderedGeometricalSets.Item("ICEM_Subline_01")
        DocumentObject.Selection.VisProperties.SetShow 0
        
        
        SaveDir_Subline_01 = SaveDir & "_SUBLINE_01.model"

        If Dir(SaveDir_Subline_01) <> "" Then
            Kill SaveDir_Subline_01
        End If

        DocumentObject.ExportData SaveDir_Subline_01, "model"
        
        
        DocumentObject.Selection.VisProperties.SetShow 1
        DocumentObject.Selection.Clear

    End If


    'Subline_12
    If Err.Number = 0 Then

        DocumentObject.Selection.Add Scale_ICEM_Subline_12_Spline_Tran_z_Point_Reduce
        DocumentObject.Selection.Add Scale_ICEM_Subline_12_Spline_Tran_Tip_Point_Reduce
        DocumentObject.Selection.Add Scale_ICEM_Subline_12_Spline_Tran_x_Reduce
        DocumentObject.Selection.Add Scale_ICEM_Subline_12_Spline_Tran_y_Reduce
        DocumentObject.Selection.Add Scale_ICEM_Subline_12_Spline_Tran_z
        DocumentObject.Selection.Add Scale_ICEM_Subline_12_Spline_Tran_Tip_xyz
        DocumentObject.Selection.VisProperties.SetShow 0
        
        
        SaveDir_Subline_12 = SaveDir & "_SUBLINE_12.model"

        If Dir(SaveDir_Subline_12) <> "" Then
            Kill SaveDir_Subline_12
        End If

        DocumentObject.ExportData SaveDir_Subline_12, "model"
        
        
        DocumentObject.Selection.VisProperties.SetShow 1
        DocumentObject.Selection.Clear

    End If


    'Subline_23
    If Err.Number = 0 Then

        DocumentObject.Selection.Add Scale_ICEM_Subline_23_Spline_Tran_z_Point
        DocumentObject.Selection.Add Scale_ICEM_Subline_23_Spline_Tran_Tip_Point
        DocumentObject.Selection.Add Scale_ICEM_Subline_23_Spline_Tran_x
        DocumentObject.Selection.Add Scale_ICEM_Subline_23_Spline_Tran_y
        DocumentObject.Selection.Add Scale_ICEM_Subline_23_Spline_Tran_z
        DocumentObject.Selection.Add Scale_ICEM_Subline_23_Spline_Tran_Tip_xyz
        DocumentObject.Selection.VisProperties.SetShow 0
        
        
        SaveDir_Subline_23 = SaveDir & "_SUBLINE_23.model"

        If Dir(SaveDir_Subline_23) <> "" Then
            Kill SaveDir_Subline_23
        End If

        DocumentObject.ExportData SaveDir_Subline_23, "model"
        
        
        DocumentObject.Selection.VisProperties.SetShow 1
        DocumentObject.Selection.Clear

    End If
    
    
    DocumentObject.Selection.Add DocumentObject.Part.OrderedGeometricalSets.Item("PLANE")
    DocumentObject.Selection.Add DocumentObject.Part.OrderedGeometricalSets.Item("PLANE").HybridShapes.Item("SectionShape")

    DocumentObject.Selection.VisProperties.SetShow 0
    DocumentObject.Selection.Clear
    
    
End Function
    

'*****************************
'FluentMeshing
'*****************************
Function FluentMeshing(ByVal DocumentObject As Object, ByVal SaveDir As String, ByVal Act_SaveStl As Integer, ByVal Act_SaveIgs As Integer, ByVal Zoom_Local_1 As Double)
    
    '-----------------------------------
    'Export .CATPart
    '-----------------------------------
    If Err.Number <> 0 Then
    
        SaveDir_CATPart = SaveDir & ".CATPart.Error"
        
        DocumentObject.SaveAs SaveDir_CATPart
    
    Else
        
        DocumentObject.Part.InWorkObject = DocumentObject.Part.OrderedGeometricalSets.Item("PLANE")
        
        
        DocumentObject.Selection.Add DocumentObject.Part.OrderedGeometricalSets.Item("PLANE")
        DocumentObject.Selection.Add DocumentObject.Part.OrderedGeometricalSets.Item("PLANE").HybridShapes.Item("SectionShape")
    
        DocumentObject.Selection.VisProperties.SetShow 1
        DocumentObject.Selection.Clear
        
        
        Set View = CATIA.ActiveWindow.ActiveViewer
        Set ViewPoint = View.Viewpoint3D
        ViewPoint.Zoom = Zoom_Local_1
        View.Update
        
        
        SaveDir_CATPart = SaveDir & ".CATPart"
            
        'If Dir(SaveDir_CATPart) <> "" Then
        '    Kill SaveDir_CATPart
        'End If
    
        DocumentObject.SaveAs SaveDir_CATPart
    
    End If
    
    
    '-----------------------------------
    'Export .stl
    '-----------------------------------
    If Err.Number = 0 And Act_SaveStl = 1 Then
        
        DocumentObject.Selection.Add DocumentObject.Part.OrderedGeometricalSets.Item("PLANE")

        DocumentObject.Selection.VisProperties.SetShow 0
        DocumentObject.Selection.Clear
        
        DocumentObject.Selection.Add DocumentObject.Part.OrderedGeometricalSets.Item("BOI_FLUID")
        DocumentObject.Selection.Add DocumentObject.Part.OrderedGeometricalSets.Item("IN")
        DocumentObject.Selection.Add DocumentObject.Part.OrderedGeometricalSets.Item("BOI_LEAD")
    
        DocumentObject.Selection.VisProperties.SetShow 1
        DocumentObject.Selection.Clear
        
        
        SaveDir_Stl = SaveDir & ".stl"
        
        If Dir(SaveDir_Stl) <> "" Then
            Kill SaveDir_Stl
        End If

        DocumentObject.ExportData SaveDir_Stl, "stl"

    End If
    
    
    '-----------------------------------
    'Export .igs
    '-----------------------------------
    If Err.Number = 0 And Act_SaveIgs = 1 Then
                
        SaveDir_Igs = SaveDir & ".igs"
        
        If Dir(SaveDir_Igs) <> "" Then
            Kill SaveDir_Igs
        End If

        DocumentObject.ExportData SaveDir_Igs, "igs"

    End If

End Function

Attribute VB_Name = "Geometry_Basic"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'DefDirection
'*****************************
Function DefDirection(ByVal DocumentObject As Object, ByVal Num_Section As Integer, ByVal Num_PointPerSpline As Integer, ByVal Data_SectionPoint As Variant) As Type_DefDirection
    
    'CreateOrderGeometry
    Set WorkObject = DocumentObject.Part.OrderedGeometricalSets.Add()
    DocumentObject.Part.OrderedGeometricalSets.Item(1).Name = "PLANE"
        
        
    Set DPH = DocumentObject.Part.HybridShapeFactory
    
    Num_Spline = Num_Section * 2
    
    
    '-----------------------------------
    'Define
    '-----------------------------------
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
    
    
    '-----------------------------------
    'Create Direction
    '-----------------------------------
    For nSection = 1 To Num_Section
        
        '-----------------------------------
        'Create Point
        '-----------------------------------
        Dim Point(1 To MaxNum_Array) As Object
        
        X1_Lead = Data_SectionPoint((nSection - 1) * Num_PointPerSpline + 1, 1)
        Y1_Lead = Data_SectionPoint((nSection - 1) * Num_PointPerSpline + 1, 2)
        Z1_Lead = Data_SectionPoint((nSection - 1) * Num_PointPerSpline + 1, 3)
        
        Set Point(1) = DPH.AddNewPointCoord(X1_Lead, Y1_Lead, Z1_Lead)
                
        
        X1_Trail = (Data_SectionPoint(nSection * Num_PointPerSpline, 1) + Data_SectionPoint((Num_Spline - nSection + 1) * Num_PointPerSpline, 1)) / 2
        Y1_Trail = (Data_SectionPoint(nSection * Num_PointPerSpline, 2) + Data_SectionPoint((Num_Spline - nSection + 1) * Num_PointPerSpline, 2)) / 2
        Z1_Trail = (Data_SectionPoint(nSection * Num_PointPerSpline, 3) + Data_SectionPoint((Num_Spline - nSection + 1) * Num_PointPerSpline, 3)) / 2
        
        Set Point(3) = DPH.AddNewPointCoord(X1_Trail, Y1_Trail, Z1_Trail)
        
        
        X1_Mid = (X1_Lead + X1_Trail) / 2
        Y1_Mid = (Y1_Lead + Y1_Trail) / 2 + 0.1 * Length_Chord(nSection)
        Z1_Mid = (Z1_Lead + Z1_Trail) / 2
        
        Set Point(2) = DPH.AddNewPointCoord(X1_Mid, Y1_Mid, Z1_Mid)
        
        
        '-----------------------------------
        'Create Flat
        '-----------------------------------
        Dim DirectionRef_Flat(1 To MaxNum_Array) As Object
    
        Set DirectionRef_Flat(nSection) = DPH.AddNewPlane3Points(Point(1), Point(2), Point(3))
    
        'WorkObject.InsertHybridShape DirectionRef_Flat(nSection)
                    
            
        '-----------------------------------
        'Create Direction
        '-----------------------------------
        Dim Direction(1 To MaxNum_Array) As Object
        
        Set Direction(nSection) = DPH.AddNewDirection(DirectionRef_Flat(nSection))
        
    Next nSection
    
    
    '-----------------------------------
    'Return
    '-----------------------------------
    ReDim DefDirection.Direction(1 To Num_Section)
    For nSection = 1 To Num_Section
    
        Set DefDirection.Direction(nSection) = Direction(nSection)
    
    Next nSection
    
End Function


'*****************************
'GenWing
'*****************************
Function GenWing(ByVal DocumentObject As Object, _
                 ByRef Entity_DefDirection As Type_DefDirection, _
                 ByVal Data_SectionPoint As Variant, ByVal Num_Section As Integer, ByVal Num_PointPerSpline As Integer, _
                 ByVal Index_SurfConnect As Variant, ByVal Mode_GuideLine As Integer, _
                 ByVal Act_Demo As Integer) _
                 As Type_GenWing
    
    'Get WorkObject
    Set WorkObject = DocumentObject.Part.OrderedGeometricalSets.Item("PLANE")
    
    
    Set DPH = DocumentObject.Part.HybridShapeFactory
    
    Num_Spline = Num_Section * 2
    
    Dim EmptyObject As Object
    
    
    '-----------------------------------
    'Create Spline_UpLow
    '-----------------------------------
    Set Extract_SectionShape = DPH.AddNewExtractMulti(EmptyObject)
    WorkObject.InsertHybridShape Extract_SectionShape
    
    Extract_SectionShape.Name = "SectionShape"
    
    nSection = 0
    For nSpline = 1 To Num_Spline
        
        nStart = (nSpline - 1) * Num_PointPerSpline + 1
        nEnd = nSpline * Num_PointPerSpline
        
        If nSpline < Num_Section + 1 Then
            nSection = nSection + 1
        ElseIf nSpline > Num_Section + 1 Then
            nSection = nSection - 1
        End If
        
        
        '-----------------------------------
        'Create Point
        '-----------------------------------
        Dim Point(1 To MaxNum_Array_Point) As Object
        
        For i = nStart To nEnd
        
            X1 = Data_SectionPoint(i, 1)
            Y1 = Data_SectionPoint(i, 2)
            Z1 = Data_SectionPoint(i, 3)
            
            Set Point(i) = DPH.AddNewPointCoord(X1, Y1, Z1)
            
            'WorkObject.InsertHybridShape Point(i)
                
        Next i
        
        
        '-----------------------------------
        'Create Spline
        '-----------------------------------
        Dim Spline_UpLow(1 To MaxNum_Array) As Object
        
        Set Spline_UpLow(nSpline) = DPH.AddNewSpline
        
        If nSpline < Num_Section + 1 Then
            Orientation = -1
        Else
            Orientation = 1
        End If
        
        For i = nStart To nEnd
            
            If i < (nStart + nEnd) / 2 Then
                Distance = Sqr((Data_SectionPoint(i, 1) - Data_SectionPoint(nStart, 1)) ^ 2 + (Data_SectionPoint(i, 3) - Data_SectionPoint(nStart, 3)) ^ 2)
            Else
                Distance = Sqr((Data_SectionPoint(i, 1) - Data_SectionPoint(nEnd, 1)) ^ 2 + (Data_SectionPoint(i, 3) - Data_SectionPoint(nEnd, 3)) ^ 2)
            End If
        
            If i = nStart Then
            
                Spline_UpLow(nSpline).AddPointWithConstraintExplicit Point(i), Entity_DefDirection.Direction(nSection), -1#, Orientation, Nothing, 0#
                
            ElseIf i = nEnd Then
            
                Spline_UpLow(nSpline).AddPointWithConstraintExplicit Point(i), Nothing, -1#, Orientation, Nothing, 0#
                
            Else
            
                If Distance > 0.005 Then
                    Spline_UpLow(nSpline).AddPointWithConstraintExplicit Point(i), Nothing, -1#, Orientation, Nothing, 0#
                End If
                
            End If
        Next i
        
        Spline_UpLow(nSpline).SetSplineType 0
        Spline_UpLow(nSpline).SetClosing 0
        
        Extract_SectionShape.AddConstraintTolerant Spline_UpLow(nSpline), 3, False, False, 0.1, 0.5, 0.98, 1
        Extract_SectionShape.SetElement 1, Spline_UpLow(nSpline)
        
    Next nSpline
    
    DocumentObject.Part.Update
    
    
    '-----------------------------------
    'Create Line_Guide
    '-----------------------------------
    Dim Index_nSection_Init(1 To MaxNum_Array)
    Dim Index_nSection_End(1 To MaxNum_Array)
    
    Dim Line_Guide_Total_Sub(1 To MaxNum_Array, 1 To 4) As Object
    Dim Line_Guide_Total(1 To 4) As Object
    
    
    'Solve Index_nSection_Init & End
    nSection_Init = 1
    nSection_End = 1
    
    Num_Connect = UBound(Index_SurfConnect) - LBound(Index_SurfConnect) + 1
    
    For nC = 1 To Num_Connect
        
        Num_Surf_PerConnect = Index_SurfConnect(nC)
        
        nSection_End = nSection_End + Num_Surf_PerConnect
        
        Index_nSection_Init(nC) = nSection_Init
        Index_nSection_End(nC) = nSection_End
        
        nSection_Init = nSection_Init + Num_Surf_PerConnect
        
    Next nC
        
        
    'Create Line_Guide_Total_Sub
    For nC = 1 To Num_Connect
        
        For i = 1 To 2
            If Mode_GuideLine = 1 Then
            
                Set Line_Guide_Total_Sub(nC, i) = DPH.AddNewPolyline
                
            ElseIf Mode_GuideLine = 2 Then
            
                Set Line_Guide_Total_Sub(nC, i) = DPH.AddNewSpline
                
            End If
        Next i
        
        For nSection = Index_nSection_Init(nC) To Index_nSection_End(nC)
            
            Set Point(1) = DPH.AddNewPointOnCurveFromPercent(Spline_UpLow(nSection), 0, False)
            
            Set Point(2) = DPH.AddNewPointOnCurveFromPercent(Spline_UpLow(nSection), 1, False)

            
            For i = 1 To 2
                If Mode_GuideLine = 1 Then
                
                    Line_Guide_Total_Sub(nC, i).InsertElement Point(i), nSection - Index_nSection_Init(nC) + 1
                
                ElseIf Mode_GuideLine = 2 Then
                
                    Line_Guide_Total_Sub(nC, i).AddPointWithConstraintExplicit Point(i), Nothing, -1#, Orientation, Nothing, 0#
                
                End If
            Next i
        
        Next nSection
    
    Next nC
    
    
    'Create Line_Guide_Total
    For i = 1 To 2
    
        If Num_Connect = 1 Then
            
            Line_Guide_Total(i) = Line_Guide_Total_Sub(1, i)

        Else
            
            Set Line_Guide_Total(i) = DPH.AddNewJoin(Line_Guide_Total_Sub(1, i), Line_Guide_Total_Sub(2, i))
            
            For nC = 3 To Num_Connect
                For nSection = 3 To Num_Section - 1

                    Line_Guide_Total(i).AddElement Line_Guide_Total_Sub(nC, i)
                        
                Next nSection
            Next nC
        
        End If

    Next i

       
    '-----------------------------------
    'Create Surface
    '-----------------------------------
    Dim Surface_UpLow(1 To MaxNum_Array) As Object
    Dim Surface_Tip_Fill As Object
    
    For nSpline = 1 To Num_Spline - 1
    
        'Loft_Up&Low
        If nSpline <> Num_Section Then
        
            nSurface = nSurface + 1
    
            Set Surface_UpLow(nSurface) = DPH.AddNewLoft
    
            Surface_UpLow(nSurface).AddSectionToLoft Spline_UpLow(nSpline), 1, Nothing
            Surface_UpLow(nSurface).AddSectionToLoft Spline_UpLow(nSpline + 1), 1, Nothing
            
            Surface_UpLow(nSurface).AddGuide Line_Guide_Total(1)
            Surface_UpLow(nSurface).AddGuide Line_Guide_Total(2)
            
            WorkObject.InsertHybridShape Surface_UpLow(nSurface)
        
        'Fill_Wingtip
        ElseIf nSpline = Num_Section Then
        
            Set Surface_Tip_Fill = DPH.AddNewFill
    
            Surface_Tip_Fill.AddBound Spline_UpLow(nSpline)
            Surface_Tip_Fill.AddBound Spline_UpLow(nSpline + 1)
            
            Surface_Tip_Fill.Continuity = 1
            Surface_Tip_Fill.Detection = 2
            Surface_Tip_Fill.AdvancedTolerantMode = 2
            
            WorkObject.InsertHybridShape Surface_Tip_Fill
    
        End If
    Next nSpline
    
    
    '-----------------------------------
    'Hide
    '-----------------------------------
    DocumentObject.Selection.Add DocumentObject.Part.OriginElements.PlaneXY
    DocumentObject.Selection.Add DocumentObject.Part.OriginElements.PlaneYZ
    DocumentObject.Selection.Add DocumentObject.Part.OriginElements.PlaneZX
        
    DocumentObject.Selection.Add Extract_SectionShape
    
    DocumentObject.Selection.VisProperties.SetShow 1
    DocumentObject.Selection.Clear
    
    
    '-----------------------------------
    'Return
    '-----------------------------------
    ReDim GenWing.Spline_UpLow(1 To MaxNum_Array)
    For i = 1 To Num_Spline
        
        Set GenWing.Spline_UpLow(i) = Spline_UpLow(i)
    
    Next i
    
    
    ReDim GenWing.Surface_UpLow(1 To MaxNum_Array)
    For i = 1 To (Num_Section - 1) * 2

        Set GenWing.Surface_UpLow(i) = Surface_UpLow(i)
    
    Next i
    
    
    Set GenWing.Surface_Tip_Fill = Surface_Tip_Fill
    
End Function


'*****************************
'GenWing_WithTrail
'*****************************
Function GenWing_WithTrail(ByVal DocumentObject As Object, _
                           ByRef Entity_DefDirection As Type_DefDirection, _
                           ByVal Data_SectionPoint As Variant, ByVal Num_Section As Integer, ByVal Num_PointPerSpline As Integer, ByVal Diameter_Fillet As Double, _
                           ByVal Index_SurfConnect As Variant, ByVal Mode_GuideLine As Integer, _
                           ByVal Act_Demo As Integer) _
                           As Type_GenWing_WithTrail
    
    'Get WorkObject
    Set WorkObject = DocumentObject.Part.OrderedGeometricalSets.Item("PLANE")
    
    
    Set DPH = DocumentObject.Part.HybridShapeFactory
    
    Num_Spline = Num_Section * 2
    
    Dim EmptyObject As Object
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Define
    '-----------------------------------
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
    
    
    '-----------------------------------
    'Create Spline_Original
    '-----------------------------------
    Set Extract_SectionShape = DPH.AddNewExtractMulti(EmptyObject)
    WorkObject.InsertHybridShape Extract_SectionShape
    
    Extract_SectionShape.Name = "SectionShape"
    
    nSection = 0
    For nSpline = 1 To Num_Spline
        
        nStart = (nSpline - 1) * Num_PointPerSpline + 1
        nEnd = nSpline * Num_PointPerSpline
        
        If nSpline < Num_Section + 1 Then
            nSection = nSection + 1
        ElseIf nSpline > Num_Section + 1 Then
            nSection = nSection - 1
        End If
        
        
        '-----------------------------------
        'Create Point
        '-----------------------------------
        Dim Point(1 To MaxNum_Array_Point) As Object
        
        For i = nStart To nEnd
        
            X1 = Data_SectionPoint(i, 1)
            Y1 = Data_SectionPoint(i, 2)
            Z1 = Data_SectionPoint(i, 3)
            
            Set Point(i) = DPH.AddNewPointCoord(X1, Y1, Z1)
            
            'WorkObject.InsertHybridShape Point(i)
                
        Next i


        '-----------------------------------
        'Create Spline
        '-----------------------------------
        Dim Spline_Original(1 To MaxNum_Array) As Object
        Dim Spline_Original_Extract(1 To MaxNum_Array) As Object
               
        Set Spline_Original(nSpline) = DPH.AddNewSpline
        
        If nSpline < Num_Section + 1 Then
            Orientation = -1
        Else
            Orientation = 1
        End If
        
        For i = nStart To nEnd
            
            If i < (nStart + nEnd) / 2 Then
                Distance = Sqr((Data_SectionPoint(i, 1) - Data_SectionPoint(nStart, 1)) ^ 2 + (Data_SectionPoint(i, 3) - Data_SectionPoint(nStart, 3)) ^ 2)
            Else
                Distance = Sqr((Data_SectionPoint(i, 1) - Data_SectionPoint(nEnd, 1)) ^ 2 + (Data_SectionPoint(i, 3) - Data_SectionPoint(nEnd, 3)) ^ 2)
            End If
        
            If i = nStart Then
            
                Spline_Original(nSpline).AddPointWithConstraintExplicit Point(i), Entity_DefDirection.Direction(nSection), -1#, Orientation, Nothing, 0#
                
            ElseIf i = nEnd Then
            
                Spline_Original(nSpline).AddPointWithConstraintExplicit Point(i), Nothing, -1#, Orientation, Nothing, 0#
                
            Else
            
                If Distance > 0.005 Then
                    Spline_Original(nSpline).AddPointWithConstraintExplicit Point(i), Nothing, -1#, Orientation, Nothing, 0#
                End If
                
            End If
        Next i
        
        Spline_Original(nSpline).SetSplineType 0
        Spline_Original(nSpline).SetClosing 0
             
        Extract_SectionShape.AddConstraintTolerant Spline_Original(nSpline), 3, False, False, 0.1, 0.5, 0.98, 1
        Extract_SectionShape.SetElement 1, Spline_Original(nSpline)
        
    Next nSpline
    
    DocumentObject.Part.Update
    
    
    '-----------------------------------
    'Deal Spline_Trail
    '-----------------------------------
    Dim Line_Chord(1 To MaxNum_Array) As Object
    
    Dim Line_Trail(1 To MaxNum_Array) As Object
    
    Dim Line_ToSplitTrail(1 To MaxNum_Array) As Object
    Dim Spline_UpLow(1 To MaxNum_Array) As Object
    
    
    'Create Line_Chord
    For nSection = 1 To Num_Section
    
        X1 = Data_SectionPoint((nSection - 1) * Num_PointPerSpline + 1, 1)
        Y1 = Data_SectionPoint((nSection - 1) * Num_PointPerSpline + 1, 2)
        Z1 = Data_SectionPoint((nSection - 1) * Num_PointPerSpline + 1, 3)

        Set Point_1 = DPH.AddNewPointCoord(X1, Y1, Z1)

        X1 = (Data_SectionPoint(nSection * Num_PointPerSpline, 1) + Data_SectionPoint((Num_Spline - nSection + 1) * Num_PointPerSpline, 1)) / 2
        Y1 = (Data_SectionPoint(nSection * Num_PointPerSpline, 2) + Data_SectionPoint((Num_Spline - nSection + 1) * Num_PointPerSpline, 2)) / 2
        Z1 = (Data_SectionPoint(nSection * Num_PointPerSpline, 3) + Data_SectionPoint((Num_Spline - nSection + 1) * Num_PointPerSpline, 3)) / 2
        
        Set Point_2 = DPH.AddNewPointCoord(X1, Y1, Z1)

        Set Line_Chord(nSection) = DPH.AddNewLinePtPt(Point_1, Point_2)
        
    Next nSection
    
    
    'Create Line_Trail
    For nSection = 1 To Num_Section
    
        X1 = Data_SectionPoint(nSection * Num_PointPerSpline, 1)
        Y1 = Data_SectionPoint(nSection * Num_PointPerSpline, 2)
        Z1 = Data_SectionPoint(nSection * Num_PointPerSpline, 3)

        Set Point_1 = DPH.AddNewPointCoord(X1, Y1, Z1)

        X1 = Data_SectionPoint((Num_Spline - nSection + 1) * Num_PointPerSpline, 1)
        Y1 = Data_SectionPoint((Num_Spline - nSection + 1) * Num_PointPerSpline, 2)
        Z1 = Data_SectionPoint((Num_Spline - nSection + 1) * Num_PointPerSpline, 3)

        Set Point_2 = DPH.AddNewPointCoord(X1, Y1, Z1)

        Set Line_Trail(nSection) = DPH.AddNewLinePtPt(Point_1, Point_2)
        
    Next nSection
    
    
    'Create Spline_UpLow
    For nSection = 1 To Num_Section
        
        Set Point_1 = DPH.AddNewPointOnCurveFromPercent(Line_Trail(nSection), 0.5, False)
        
        Set Point_2 = DPH.AddNewPointOnCurveWithReferenceFromDistance(Line_Chord(nSection), Point_1, Diameter_Fillet / 2, True)
        
        Set Line_ToSplitTrail(nSection) = DPH.AddNewLineAngle(Line_Chord(nSection), PLANE_ZX, Point_2, False, -0.5 * Length_Chord(nSection), 0.5 * Length_Chord(nSection), 90, False)
        
        
        For nUL = 1 To 2

            If nUL = 1 Then
                Index = nSection
            Else
                Index = Num_Spline - nSection + 1
            End If

            Set Spline_UpLow(Index) = DPH.AddNewHybridSplit(Spline_Original(Index), Line_ToSplitTrail(nSection), 1)
            
            If Act_Demo = 1 Then
                WorkObject.InsertHybridShape Spline_UpLow(Index)
            End If
            
        Next nUL
        
    Next nSection
    
    
    '-----------------------------------
    'Create Line_Guide
    '-----------------------------------
    Dim Index_nSection_Init(1 To MaxNum_Array)
    Dim Index_nSection_End(1 To MaxNum_Array)
    
    Dim Surface_ToSplit(1 To MaxNum_Array) As Object
    
    Dim Line_Guide_Total_Sub(1 To MaxNum_Array, 1 To 4) As Object
    Dim Line_Guide_Total(1 To 4) As Object
    Dim Line_Guide(1 To MaxNum_Array, 1 To 4) As Object
    
    
    'Solve Index_nSection_Init & End
    nSection_Init = 1
    nSection_End = 1
    
    Num_Connect = UBound(Index_SurfConnect) - LBound(Index_SurfConnect) + 1
    
    For nC = 1 To Num_Connect
        
        Num_Surf_PerConnect = Index_SurfConnect(nC)
        
        nSection_End = nSection_End + Num_Surf_PerConnect
        
        Index_nSection_Init(nC) = nSection_Init
        Index_nSection_End(nC) = nSection_End
        
        nSection_Init = nSection_Init + Num_Surf_PerConnect
        
    Next nC
    
    
    'Create Surface_ToSplit
    For nSection = 2 To Num_Section - 1
            
        Set Point_1 = DPH.AddNewPointOnCurveFromPercent(Spline_UpLow(nSection), 0, False)
        Set Point_2 = DPH.AddNewPointOnCurveFromPercent(Spline_UpLow(nSection), 1, False)
        
        Set Line_Direction = DPH.AddNewLinePtPt(Point_1, Point_2)
            
        Set Direction_1 = DPH.AddNewDirection(Line_Direction)
        
        
        Set Line_ToSplit = DPH.AddNewLinePtDir(Point_1, Direction_1, -Length_Chord(nSection), 2 * Length_Chord(nSection), False)
        
        Set Surface_ToSplit(nSection) = DPH.AddNewExtrude(Line_ToSplit, 0.5 * Length_Chord(nSection), 0.5 * Length_Chord(nSection), Direction_Z)
        
    Next nSection
    
        
    'Create Line_Guide_Total_Sub
    For nC = 1 To Num_Connect
        
        For i = 1 To 4
            If Mode_GuideLine = 1 Then
            
                Set Line_Guide_Total_Sub(nC, i) = DPH.AddNewPolyline
                
            ElseIf Mode_GuideLine = 2 Then
            
                Set Line_Guide_Total_Sub(nC, i) = DPH.AddNewSpline
                
            End If
        Next i
        
        For nSection = Index_nSection_Init(nC) To Index_nSection_End(nC)
            
            Set Point(1) = DPH.AddNewPointOnCurveFromPercent(Spline_UpLow(nSection), 0, False)
            
            Set Point(2) = DPH.AddNewPointOnCurveFromPercent(Spline_UpLow(nSection), 1, False)
            
            X1 = (Data_SectionPoint(nSection * Num_PointPerSpline, 1) + Data_SectionPoint((Num_Spline - nSection + 1) * Num_PointPerSpline, 1)) / 2
            Y1 = (Data_SectionPoint(nSection * Num_PointPerSpline, 2) + Data_SectionPoint((Num_Spline - nSection + 1) * Num_PointPerSpline, 2)) / 2
            Z1 = (Data_SectionPoint(nSection * Num_PointPerSpline, 3) + Data_SectionPoint((Num_Spline - nSection + 1) * Num_PointPerSpline, 3)) / 2
            
            Set Point(3) = DPH.AddNewPointCoord(X1, Y1, Z1)
            
            Set Point(4) = DPH.AddNewPointOnCurveFromPercent(Spline_UpLow(Num_Spline - nSection + 1), 1, False)
            
            
            For i = 1 To 4
                If Mode_GuideLine = 1 Then
                
                    Line_Guide_Total_Sub(nC, i).InsertElement Point(i), nSection - Index_nSection_Init(nC) + 1
                
                ElseIf Mode_GuideLine = 2 Then
                
                    Line_Guide_Total_Sub(nC, i).AddPointWithConstraintExplicit Point(i), Nothing, -1#, Orientation, Nothing, 0#
                
                End If
            Next i
        
        Next nSection
    
    Next nC
    
    
    'Create Line_Guide_Total
    For i = 1 To 4
    
        If Num_Connect = 1 Then
            
            Line_Guide_Total(i) = Line_Guide_Total_Sub(1, i)

        Else
            
            Set Line_Guide_Total(i) = DPH.AddNewJoin(Line_Guide_Total_Sub(1, i), Line_Guide_Total_Sub(2, i))
            
            For nC = 3 To Num_Connect
                For nSection = 3 To Num_Section - 1

                    Line_Guide_Total(i).AddElement Line_Guide_Total_Sub(nC, i)
                        
                Next nSection
            Next nC
        
        End If

    Next i
    
    
    'Split To Line_Guide
    For i = 1 To 4
        For nSection = 1 To Num_Section - 1
        
            If nSection = 1 Then
                
                Set Line_Guide(nSection, i) = DPH.AddNewHybridSplit(Line_Guide_Total(i), Surface_ToSplit(nSection + 1), -1)

            ElseIf nSection > 1 And nSection < Num_Section - 1 Then

                Set Line_Guide(nSection, i) = DPH.AddNewHybridSplit(Line_Guide_Total(i), Surface_ToSplit(nSection), 1)
                Set Line_Guide(nSection, i) = DPH.AddNewHybridSplit(Line_Guide(nSection, i), Surface_ToSplit(nSection + 1), -1)

            Else

                Set Line_Guide(nSection, i) = DPH.AddNewHybridSplit(Line_Guide_Total(i), Surface_ToSplit(nSection), 1)

            End If
            
            'WorkObject.InsertHybridShape Line_Guide(nSection, i)

        Next nSection
    Next i
    
    
    '-----------------------------------
    'Create Surface
    '-----------------------------------
    Dim Surface_UpLow_Total_Sub(1 To 2, 1 To MaxNum_Array) As Object
    Dim Surface_UpLow_Total(1 To 2) As Object
    
    Dim Surface_UpLow(1 To MaxNum_Array) As Object

    Dim Spline_Fillet(1 To MaxNum_Array) As Object
    Dim Surface_Fillet(1 To MaxNum_Array) As Object

    Dim Surface_Tip_Fill As Object
    
    
    'Create Line_Guide_Total
    For i = 1 To 4
    
        Set Line_Guide_Total(i) = DPH.AddNewJoin(Line_Guide(1, i), Line_Guide(2, i))
        
        For nSection = 3 To Num_Section - 1
            Line_Guide_Total(i).AddElement Line_Guide(nSection, i)
        Next nSection
        
    Next i
    
    
    'Create Surface_UpLow_Total_Sub
    For nC = 1 To Num_Connect
        For nUL = 1 To 2
    
            Set Surface_UpLow_Total_Sub(nUL, nC) = DPH.AddNewLoft
            
            For nSection = Index_nSection_Init(nC) To Index_nSection_End(nC)
                
                If nUL = 1 Then
                    Index = nSection
                Else
                    Index = Num_Spline - (Index_nSection_Init(nC) + Index_nSection_End(nC) - nSection) + 1
                End If
                
                Surface_UpLow_Total_Sub(nUL, nC).AddSectionToLoft Spline_UpLow(Index), 1, Nothing
    
            Next nSection
            
            Set Line_Guide_Total_Lead = Line_Guide_Total(1)
            If nUL = 1 Then
                Set Line_Guide_Total_Trail = Line_Guide_Total(2)
            Else
                Set Line_Guide_Total_Trail = Line_Guide_Total(4)
            End If
                
            Surface_UpLow_Total_Sub(nUL, nC).AddGuide Line_Guide_Total_Lead
            Surface_UpLow_Total_Sub(nUL, nC).AddGuide Line_Guide_Total_Trail
        
        Next nUL
    Next nC
    
    
    'Create Surface_UpLow_Total
    For nUL = 1 To 2
        
        If Num_Connect <> 1 Then
        
            If nUL = 1 Then
            
                Set Surface_UpLow_Total(nUL) = DPH.AddNewJoin(Surface_UpLow_Total_Sub(nUL, 1), Surface_UpLow_Total_Sub(nUL, 2))
                
                For nC = 3 To Num_Connect
                    
                    Surface_UpLow_Total(nUL).AddElement Surface_UpLow_Total_Sub(nUL, nC)
                    
                Next nC
            
            ElseIf nUL = 2 Then
            
                Set Surface_UpLow_Total(nUL) = DPH.AddNewJoin(Surface_UpLow_Total_Sub(nUL, Num_Connect), Surface_UpLow_Total_Sub(nUL, Num_Connect - 1))
                
                For nC = Num_Connect - 2 To 1 Step -1
                    
                    Surface_UpLow_Total(nUL).AddElement Surface_UpLow_Total_Sub(nUL, nC)
                    
                Next nC
            
            End If
        
        Else
        
            Set Surface_UpLow_Total(nUL) = Surface_UpLow_Total_Sub(nUL, 1)
        
        End If
        
        If Act_Demo = 1 Then
            WorkObject.InsertHybridShape Surface_UpLow_Total(nUL)
        End If
    
    Next nUL
    
    
    'Split To Surface_UpLow
    nSurface = 0
    
    For nSection = 1 To Num_Section - 1

        For nUL = 1 To 2
            
            If nUL = 1 Then
                nSurface = nSection
            Else
                nSurface = (Num_Section - 1) * 2 - nSection + 1
            End If
            
            
            If nSection = 1 Then
            
                Set Surface_UpLow(nSurface) = DPH.AddNewHybridSplit(Surface_UpLow_Total(nUL), Surface_ToSplit(nSection + 1), 1)
            
            ElseIf nSection > 1 And nSection < Num_Section - 1 Then
            
                Set Surface_UpLow(nSurface) = DPH.AddNewHybridSplit(Surface_UpLow_Total(nUL), Surface_ToSplit(nSection), -1)
                Set Surface_UpLow(nSurface) = DPH.AddNewHybridSplit(Surface_UpLow(nSurface), Surface_ToSplit(nSection + 1), 1)
            
            Else
            
                Set Surface_UpLow(nSurface) = DPH.AddNewHybridSplit(Surface_UpLow_Total(nUL), Surface_ToSplit(nSection), -1)
            
            End If
            
            If Act_Demo = 1 Then
                WorkObject.InsertHybridShape Surface_UpLow(nSurface)
            End If
            
        Next nUL

    Next nSection
    
    
    'Fillet
    For nSection = 1 To Num_Section

        Set Point_1 = DPH.AddNewPointOnCurveFromPercent(Spline_UpLow(nSection), 1, False)
        
        Set Point_2 = DPH.AddNewPointOnCurveFromPercent(Line_Trail(nSection), 0.5, False)
        
        Set Point_3 = DPH.AddNewPointOnCurveFromPercent(Spline_UpLow(Num_Spline - nSection + 1), 1, False)

        Set Spline_Fillet(nSection) = DPH.AddNewSpline
        Spline_Fillet(nSection).AddPointWithConstraintFromCurve Point_1, Spline_UpLow(nSection), 1, 1, 1
        Spline_Fillet(nSection).AddPointWithConstraintFromCurve Point_2, Line_Trail(nSection), 1, 1, 1
        Spline_Fillet(nSection).AddPointWithConstraintFromCurve Point_3, Spline_UpLow(Num_Spline - nSection + 1), 1, -1, 1
              
        If Act_Demo = 1 Then
            WorkObject.InsertHybridShape Spline_Fillet(nSection)
        End If

    Next nSection


    For nSection = 1 To Num_Section - 1
        
        Set Surface_Fillet(nSection) = DPH.AddNewLoft

        Surface_Fillet(nSection).AddSectionToLoft Spline_Fillet(nSection), 1, Nothing
        Surface_Fillet(nSection).AddSectionToLoft Spline_Fillet(nSection + 1), 1, Nothing

        Surface_Fillet(nSection).AddGuideWithTangent Line_Guide(nSection, 2), Surface_UpLow(nSection)
        Surface_Fillet(nSection).AddGuideWithTangent Line_Guide(nSection, 4), Surface_UpLow(Num_Spline - nSection - 1)
        
        If Act_Demo = 1 Then
            WorkObject.InsertHybridShape Surface_Fillet(nSection)
        End If
              
    Next nSection
    

    'Fill_Wingtip
    Set Surface_Tip_Fill = DPH.AddNewFill

    Surface_Tip_Fill.AddBound Spline_UpLow(Num_Section)
    Surface_Tip_Fill.AddBound Spline_Fillet(Num_Section)
    Surface_Tip_Fill.AddBound Spline_UpLow(Num_Section + 1)

    Surface_Tip_Fill.Continuity = 1
    Surface_Tip_Fill.Detection = 2
    Surface_Tip_Fill.AdvancedTolerantMode = 2

    If Act_Demo = 1 Then
        WorkObject.InsertHybridShape Surface_Tip_Fill
    End If
    
    
    '-----------------------------------
    'Hide
    '-----------------------------------
    DocumentObject.Selection.Add DocumentObject.Part.OriginElements.PlaneXY
    DocumentObject.Selection.Add DocumentObject.Part.OriginElements.PlaneYZ
    DocumentObject.Selection.Add DocumentObject.Part.OriginElements.PlaneZX
    
    DocumentObject.Selection.Add Extract_SectionShape
    
    If Act_Demo = 1 Then
        For nSection = 2 To Num_Section - 1
            DocumentObject.Selection.Add Surface_ToSplit(nSection)
        Next nSection
        
        For nSpline = 1 To Num_Spline
            DocumentObject.Selection.Add Spline_UpLow(nSpline)
        Next nSpline
        
        For nSection = 1 To Num_Section
            DocumentObject.Selection.Add Line_ToSplitTrail(nSection)
        Next nSection
        
        For nSection = 1 To Num_Section
            DocumentObject.Selection.Add Spline_Fillet(nSection)
        Next nSection
    End If
    
    DocumentObject.Selection.VisProperties.SetShow 1
    DocumentObject.Selection.Clear
    
    
    '-----------------------------------
    'Return
    '-----------------------------------
    ReDim GenWing_WithTrail.Line_Guide(1 To MaxNum_Array, 1 To 4)
    For nSection = 1 To Num_Section - 1
        For i = 1 To 4
            
            Set GenWing_WithTrail.Line_Guide(nSection, i) = Line_Guide(nSection, i)
        
        Next i
    Next nSection
       
       
    ReDim GenWing_WithTrail.Spline_Original(1 To MaxNum_Array)
    For i = 1 To Num_Spline
        
        Set GenWing_WithTrail.Spline_Original(i) = Spline_Original(i)
    
    Next i
              
              
    ReDim GenWing_WithTrail.Spline_UpLow(1 To MaxNum_Array)
    For i = 1 To Num_Spline
        
        Set GenWing_WithTrail.Spline_UpLow(i) = Spline_UpLow(i)
    
    Next i
        
        
    ReDim GenWing_WithTrail.Spline_Fillet(1 To MaxNum_Array)
    For i = 1 To Num_Section
        
        Set GenWing_WithTrail.Spline_Fillet(i) = Spline_Fillet(i)
    
    Next i
    
    
    ReDim GenWing_WithTrail.Surface_UpLow(1 To MaxNum_Array)
    For i = 1 To (Num_Section - 1) * 2
        
        Set GenWing_WithTrail.Surface_UpLow(i) = Surface_UpLow(i)
    
    Next i


    ReDim GenWing_WithTrail.Surface_Fillet(1 To MaxNum_Array)
    For i = 1 To Num_Section - 1
        
        Set GenWing_WithTrail.Surface_Fillet(i) = Surface_Fillet(i)
    
    Next i
    
    
    Set GenWing_WithTrail.Surface_Tip_Fill = Surface_Tip_Fill
    
End Function

Attribute VB_Name = "Geometry_Post"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'FluentMeshing
'*****************************
Function FluentMeshing(ByVal DocumentObject As Object, _
                       ByRef Entity_SmoothAndJoint As Type_SmoothAndJoint, _
                       ByVal Data_SectionPoint As Variant, ByVal Data_LeadPoint As Variant, ByVal Num_Section As Integer, ByVal Num_PointPerSpline As Integer, _
                       ByVal MAC_Length As Double, ByVal MAC_x As Double, _
                       ByVal Diameter_Fillet As Double, ByVal Rate_Fluid As Double, ByVal Rate_BOI_Fluid_MAC As Double, ByVal Rate_BOI_Fluid_Span As Double)
    
    Set DPH = DocumentObject.Part.HybridShapeFactory
    
    Num_Spline = Num_Section * 2
    
    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
                              
                       
    '-----------------------------------
    'Define
    '-----------------------------------
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
    
    
    '-----------------------------------
    'OrderGeometry_PLANE
    '-----------------------------------
    'Get WorkObject
    Set WorkObject = DocumentObject.Part.OrderedGeometricalSets.Item("PLANE")
    
    
    'Joint
    Set Surface_Plane = DPH.AddNewJoin(Entity_SmoothAndJoint.Surface_Joint_UpLow_Up, Entity_SmoothAndJoint.Surface_Joint_UpLow_Low)
        
    Surface_Plane.AddElement Entity_SmoothAndJoint.Surface_Joint_Tip
    Surface_Plane.AddElement Entity_SmoothAndJoint.Surface_Joint_Fillet
    
    WorkObject.InsertHybridShape Surface_Plane
    
    
    'Symm
    Set Surface_Plane_Symm = DPH.AddNewSymmetry(Surface_Plane, PLANE_ZX)

    WorkObject.InsertHybridShape Surface_Plane_Symm
    
        
    'Hide
    DocumentObject.Selection.Add Surface_Plane_Symm
     
    DocumentObject.Selection.VisProperties.SetShow 1
    DocumentObject.Selection.Clear
    
    
    '-----------------------------------
    'OrderGeometry_BOI_FLUID
    '-----------------------------------
    'CreateOrderGeometry
    Set WorkObject = DocumentObject.Part.OrderedGeometricalSets.Add()
    DocumentObject.Part.OrderedGeometricalSets.Item(2).Name = "BOI_FLUID"
    
    
    Dim Point_BOI_Fluid(1 To MaxNum_Array) As Object
    
    Radius_BOI_Fluid = Rate_BOI_Fluid_MAC * MAC_Length
    
    
    'Creat Point
    X1 = MAC_x + Length_Chord(1) / 2
    Y1 = 0
    Z1 = 0

    Set Point_BOI_Fluid(1) = DPH.AddNewPointCoord(X1, Y1, Z1)
    
    X1 = X1
    Y1 = Y1
    Z1 = Z1 + Radius_BOI_Fluid

    Set Point_BOI_Fluid(2) = DPH.AddNewPointCoord(X1, Y1, Z1)
    
    X1 = X1
    Y1 = Y1
    Z1 = Z1 - 2 * Radius_BOI_Fluid

    Set Point_BOI_Fluid(3) = DPH.AddNewPointCoord(X1, Y1, Z1)
    

    'Creat Solid
    Set Circle_BOI_Fluid = DPH.AddNewCircleCtrRadWithAngles(Point_BOI_Fluid(1), PLANE_ZX, False, Radius_BOI_Fluid, -90, 90)
    
    Set Axis_BOI_Fluid = DPH.AddNewLinePtPt(Point_BOI_Fluid(2), Point_BOI_Fluid(3))

    Set Solid_BOI_Fluid = DPH.AddNewRevol(Circle_BOI_Fluid, 0, 180, Axis_BOI_Fluid)
    Solid_BOI_Fluid.Context = 1


    'Change To Ellipse
    Span_Half = Data_SectionPoint(Num_Section * Num_PointPerSpline, 2) - Data_SectionPoint(Num_PointPerSpline, 2)
    
    Radius_BOI_Fluid_BasedMAC = Rate_BOI_Fluid_MAC * MAC_Length
    Radius_BOI_Fluid_BasedSpan = Rate_BOI_Fluid_Span * Span_Half
    
    
    Rate_x = 1
    
    If Radius_BOI_Fluid_BasedSpan > Radius_BOI_Fluid_BasedMAC Then
        Rate_y = Radius_BOI_Fluid_BasedSpan / Radius_BOI_Fluid
    Else
        Rate_y = (Radius_BOI_Fluid_BasedSpan + Radius_BOI_Fluid_BasedMAC) / 2 / Radius_BOI_Fluid
    End If
    
    Rate_z = 1
    
    Set Solid_BOI_Fluid_Ellipse = DPH.AddNewAffinity(Solid_BOI_Fluid, Rate_x, Rate_y, Rate_z)
    
    Solid_BOI_Fluid_Ellipse.AxisOrigin = Point_BOI_Fluid(1)
    Solid_BOI_Fluid_Ellipse.VolumeResult = True
    
    WorkObject.InsertHybridShape Solid_BOI_Fluid_Ellipse

 
    '-----------------------------------
    'OrderGeometry_IN
    '-----------------------------------
    'CreateOrderGeometry
    Set WorkObject = DocumentObject.Part.OrderedGeometricalSets.Add()
    DocumentObject.Part.OrderedGeometricalSets.Item(3).Name = "IN"
    
    
    Dim Point_Fluid(1 To MaxNum_Array) As Object
    
    'Radius_Fluid = Rate_Fluid * Length_Chord(1)
    Radius_Fluid = Rate_Fluid * MAC_Length
    
    'Create Point
    X1 = Length_Chord(1) / 2
    Y1 = 0
    Z1 = 0

    Set Point_Fluid(1) = DPH.AddNewPointCoord(X1, Y1, Z1)
    
    X1 = X1
    Y1 = Y1
    Z1 = Z1 + Radius_Fluid

    Set Point_Fluid(2) = DPH.AddNewPointCoord(X1, Y1, Z1)
    
    X1 = X1
    Y1 = Y1
    Z1 = Z1 - 2 * Radius_Fluid

    Set Point_Fluid(3) = DPH.AddNewPointCoord(X1, Y1, Z1)
    
    
    'Create Solid
    Set Circle_Fluid = DPH.AddNewCircleCtrRadWithAngles(Point_Fluid(1), PLANE_ZX, False, Radius_Fluid, -90, 90)
    
    Set Axis_Fluid = DPH.AddNewLinePtPt(Point_Fluid(2), Point_Fluid(3))
    
    Set Solid_Fluid = DPH.AddNewRevol(Circle_Fluid, 0, 180, Axis_Fluid)
    Solid_Fluid.Context = 1
    
    
    'Split Solid
    Set Solid_Fluid_Split = DPH.AddNewHybridSplit(Solid_Fluid, Surface_Plane_Symm, 1)
    Solid_Fluid_Split.VolumeResult = 1
    
    WorkObject.InsertHybridShape Solid_Fluid_Split
    
    
    '-----------------------------------
    'OrderGeometry_BOI_LEAD
    '-----------------------------------
    Dim Point_BOI_LEAD_Basic(1 To MaxNum_Array) As Object
    Dim Point_BOI_LEAD_Project(1 To MaxNum_Array) As Object
    
    Dim Circle_BOI_LEAD(1 To MaxNum_Array) As Object
    Dim Polyline_BOI_LEAD(1 To MaxNum_Array) As Object
    Dim Surface_BOI_LEAD_Basic(1 To MaxNum_Array) As Object
    
    
    'CreateOrderGeometry
    Set WorkObject = DocumentObject.Part.OrderedGeometricalSets.Add()
    DocumentObject.Part.OrderedGeometricalSets.Item(4).Name = "BOI_LEAD"
    
    
    'Creat Point_Basic
    Num_Interp = 3
    
    For nSection = 1 To Num_Section
    
        If nSection = Num_Section Then
        
            X1 = Data_LeadPoint(nSection, 1)
            Y1 = Data_LeadPoint(nSection, 2)
            Z1 = Data_LeadPoint(nSection, 3)
            
            Set Point_BOI_LEAD_Basic((nSection - 1) * Num_Interp + 1) = DPH.AddNewPointCoord(X1, Y1, Z1)
                
            'WorkObject.InsertHybridShape Point_BOI_LEAD_Basic((nSection - 1) * Num_Interp + 1)
                
        Else
        
            X1 = Data_LeadPoint(nSection, 1)
            Y1 = Data_LeadPoint(nSection, 2)
            Z1 = Data_LeadPoint(nSection, 3)
        
            X2 = Data_LeadPoint(nSection + 1, 1)
            Y2 = Data_LeadPoint(nSection + 1, 2)
            Z2 = Data_LeadPoint(nSection + 1, 3)
            
            For nInterp = 1 To Num_Interp
            
                X_Cache = X1 + (X2 - X1) * (nInterp - 1) / Num_Interp
                Y_Cache = Y1 + (Y2 - Y1) * (nInterp - 1) / Num_Interp
                Z_Cache = Z1 + (Z2 - Z1) * (nInterp - 1) / Num_Interp
                
                Set Point_BOI_LEAD_Basic((nSection - 1) * Num_Interp + nInterp) = DPH.AddNewPointCoord(X_Cache, Y_Cache, Z_Cache)
                
                'WorkObject.InsertHybridShape Point_BOI_LEAD_Basic((nSection - 1) * Num_Interp + nInterp)
                
            Next nInterp
            
        End If
    
    Next nSection


    'Creat Point_Project
    For nPoint = 1 To (Num_Section - 1) * Num_Interp + 1
        
        If nPoint = 1 Or nPoint = (Num_Section - 1) * Num_Interp + 1 Then
        
            Set Point_BOI_LEAD_Project(nPoint) = Point_BOI_LEAD_Basic(nPoint)
            
        Else
        
            Set Point_BOI_LEAD_Project(nPoint) = DPH.AddNewProject(Point_BOI_LEAD_Basic(nPoint), Surface_Plane)
    
            Point_BOI_LEAD_Project(nPoint).Normal = True
            
            'WorkObject.InsertHybridShape Point_BOI_LEAD_Project(nPoint)
            
        End If
                
    Next nPoint


    'Creat Circle
    Radius_BOI_Lead = Diameter_Fillet * 2
    
    For nCircle = 1 To (Num_Section - 1) * Num_Interp + 1
            
        Set Circle_BOI_LEAD(nCircle) = DPH.AddNewCircleCtrRadWithAngles(Point_BOI_LEAD_Project(nCircle), PLANE_ZX, False, Radius_BOI_Lead, 0, 360)
        
        'WorkObject.InsertHybridShape Circle_BOI_LEAD(nCircle)
    
    Next nCircle
    
    
    'Create Polyline
    For nPanel = 1 To Num_Section - 1
            
        Set Polyline_BOI_LEAD(nPanel) = DPH.AddNewPolyline
        
        For nPoint = (nPanel - 1) * Num_Interp + 1 To nPanel * Num_Interp + 1
        
            Polyline_BOI_LEAD(nPanel).InsertElement Point_BOI_LEAD_Project(nPoint), nPoint
            
        Next nPoint
        
        'WorkObject.InsertHybridShape Polyline_BOI_LEAD(nPanel)
        
    Next nPanel
    
    
    'Create Surface_Basic
    For nPanel = 1 To Num_Section - 1
            
        Set Surface_BOI_LEAD_Basic(nPanel) = DPH.AddNewLoft
        
        For nCircle = (nPanel - 1) * Num_Interp + 1 To nPanel * Num_Interp + 1
        
            Surface_BOI_LEAD_Basic(nPanel).AddSectionToLoft Circle_BOI_LEAD(nCircle), 1, Nothing
            
        Next nCircle
        
        Surface_BOI_LEAD_Basic(nPanel).SectionCoupling = 1
        Surface_BOI_LEAD_Basic(nPanel).Relimitation = 1
        Surface_BOI_LEAD_Basic(nPanel).CanonicalDetection = 2
        Surface_BOI_LEAD_Basic(nPanel).SetSpine Polyline_BOI_LEAD(nPanel)
        
        'WorkObject.InsertHybridShape Surface_BOI_LEAD_Basic(nPanel)
        
    Next nPanel
    
    
    'Joint Surface_BOI_LEAD_Basic
    Set Surface_BOI_LEAD_Basic_Joint = DPH.AddNewJoin(Surface_BOI_LEAD_Basic(1), Surface_BOI_LEAD_Basic(2))
    
    For nPanel = 3 To Num_Section - 1
        Surface_BOI_LEAD_Basic_Joint.AddElement Surface_BOI_LEAD_Basic(nPanel)
    Next nPanel
    
    
    'Extrapolate Surface_BOI_LEAD_Basic
    Set Circle_1 = Circle_BOI_LEAD((Num_Section - 1) * Num_Interp + 1)
    
    Set Surface_BOI_LEAD_Basic_Joint_Extrapolate = DPH.AddNewExtrapolLength(Circle_1, Surface_BOI_LEAD_Basic_Joint, Length_Chord(Num_Section))
    
    Surface_BOI_LEAD_Basic_Joint_Extrapolate.BorderType = 1
    Surface_BOI_LEAD_Basic_Joint_Extrapolate.SetAssemble True
    Surface_BOI_LEAD_Basic_Joint_Extrapolate.SetContinuityType 1, 1
    

    'Creat Surface_BOI_LEAD_Split
    Set Surface_BOI_LEAD_Split = DPH.AddNewHybridSplit(Surface_Plane, Surface_BOI_LEAD_Basic_Joint_Extrapolate, -1)

    
    'Symm
    Set Surface_BOI_LEAD_Split_Symm = DPH.AddNewSymmetry(Surface_BOI_LEAD_Split, PLANE_ZX)

    WorkObject.InsertHybridShape Surface_BOI_LEAD_Split_Symm
    
End Function


'*****************************
'ICEM_FluidAndBOI
'*****************************
Function ICEM_FluidAndBOI(ByVal DocumentObject As Object, _
                          ByVal Data_SectionPoint As Variant, ByVal Num_Section As Integer, ByVal Num_PointPerSpline As Integer, _
                          ByVal MAC_Length As Double, ByVal MAC_x As Double, _
                          ByVal Diameter_Fillet As Double, ByVal Rate_Fluid As Double, ByVal Rate_BOI_Fluid_MAC As Double, ByVal Rate_BOI_Fluid_Span As Double) _
                          As Type_ICEM_FluidAndBOI

    Set DPH = DocumentObject.Part.HybridShapeFactory
    
    Num_Spline = Num_Section * 2
    
    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Define
    '-----------------------------------
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
    

    '-----------------------------------
    'OrderGeometry_BOI_FLUID
    '-----------------------------------
    'CreateOrderGeometry
    Set WorkObject = DocumentObject.Part.OrderedGeometricalSets.Add()
    DocumentObject.Part.OrderedGeometricalSets.Item(2).Name = "BOI_FLUID"
    
    
    Dim Point_BOI_Fluid(1 To MaxNum_Array) As Object
    
    Radius_BOI_Fluid_BasedMAC = Rate_BOI_Fluid_MAC * MAC_Length
    
    
    'Creat Point
    X1 = Length_Chord(1) / 2
    Y1 = 0
    Z1 = 0

    Set Point_BOI_Fluid(1) = DPH.AddNewPointCoord(X1, Y1, Z1)
    
    X1 = X1
    Y1 = Y1
    Z1 = Z1 + Radius_BOI_Fluid_BasedMAC

    Set Point_BOI_Fluid(2) = DPH.AddNewPointCoord(X1, Y1, Z1)
    
    X1 = X1
    Y1 = Y1
    Z1 = Z1 - 2 * Radius_BOI_Fluid_BasedMAC

    Set Point_BOI_Fluid(3) = DPH.AddNewPointCoord(X1, Y1, Z1)
    

    'Creat Surface
    Set Circle_BOI_Fluid = DPH.AddNewCircleCtrRadWithAngles(Point_BOI_Fluid(1), PLANE_ZX, False, Radius_BOI_Fluid_BasedMAC, -90, 90)
    
    Set Axis_BOI_Fluid = DPH.AddNewLinePtPt(Point_BOI_Fluid(2), Point_BOI_Fluid(3))

    Set Surface_BOI_Fluid = DPH.AddNewRevol(Circle_BOI_Fluid, 180, 0, Axis_BOI_Fluid)
    
    WorkObject.InsertHybridShape Surface_BOI_Fluid
    
 
    '-----------------------------------
    'OrderGeometry_IN
    '-----------------------------------
    'CreateOrderGeometry
    Set WorkObject = DocumentObject.Part.OrderedGeometricalSets.Add()
    DocumentObject.Part.OrderedGeometricalSets.Item(3).Name = "IN"
    
    
    Dim Point_Fluid(1 To MaxNum_Array) As Object
    
    'Radius_Fluid = Rate_Fluid * Length_Chord(1)
    Radius_Fluid = Rate_Fluid * MAC_Length
    
    
    'Create Point
    X1 = Length_Chord(1) / 2
    Y1 = 0
    Z1 = 0

    Set Point_Fluid(1) = DPH.AddNewPointCoord(X1, Y1, Z1)
    
    X1 = X1
    Y1 = Y1
    Z1 = Z1 + Radius_Fluid

    Set Point_Fluid(2) = DPH.AddNewPointCoord(X1, Y1, Z1)
    
    X1 = X1
    Y1 = Y1
    Z1 = Z1 - 2 * Radius_Fluid

    Set Point_Fluid(3) = DPH.AddNewPointCoord(X1, Y1, Z1)
    
    
    'Create Surface
    Set Circle_Fluid = DPH.AddNewCircleCtrRadWithAngles(Point_Fluid(1), PLANE_ZX, False, Radius_Fluid, -90, 90)
    
    Set Axis_Fluid = DPH.AddNewLinePtPt(Point_Fluid(2), Point_Fluid(3))
    
    Set Surface_Fluid = DPH.AddNewRevol(Circle_Fluid, 180, 0, Axis_Fluid)

    WorkObject.InsertHybridShape Surface_Fluid
    
    
    '-----------------------------------
    'OrderGeometry_SYMM
    '-----------------------------------
    'CreateOrderGeometry
    Set WorkObject = DocumentObject.Part.OrderedGeometricalSets.Add()
    DocumentObject.Part.OrderedGeometricalSets.Item(4).Name = "SYMM"
    
    
    'Create Surface
    Set Circle_Symm = DPH.AddNewIntersection(Surface_Fluid, PLANE_ZX)
    
    Set Surface_Symm = DPH.AddNewFill
    Surface_Symm.AddBound Circle_Symm
    Surface_Symm.Continuity = 1
    Surface_Symm.Detection = 2
    Surface_Symm.AdvancedTolerantMode = 2
    
    WorkObject.InsertHybridShape Surface_Symm
        
    
    '-----------------------------------
    'Hide
    '-----------------------------------
    DocumentObject.Selection.Add DocumentObject.Part.OrderedGeometricalSets.Item("BOI_FLUID")
    DocumentObject.Selection.Add DocumentObject.Part.OrderedGeometricalSets.Item("IN")
    DocumentObject.Selection.Add DocumentObject.Part.OrderedGeometricalSets.Item("SYMM")
     
    DocumentObject.Selection.VisProperties.SetShow 1
    DocumentObject.Selection.Clear
    
    
    '-----------------------------------
    'Return
    '-----------------------------------
    ICEM_FluidAndBOI.Radius_Fluid = Radius_Fluid
    ICEM_FluidAndBOI.Radius_BOI_Fluid_BasedMAC = Radius_BOI_Fluid_BasedMAC
    
    
    Set ICEM_FluidAndBOI.Surface_BOI_Fluid = Surface_BOI_Fluid
    Set ICEM_FluidAndBOI.Surface_Fluid = Surface_Fluid
    Set ICEM_FluidAndBOI.Surface_Symm = Surface_Symm
    
    Set ICEM_FluidAndBOI.Extract_Surface_BOI_Fluid = Surface_BOI_Fluid
    Set ICEM_FluidAndBOI.Extract_Surface_Fluid = Surface_Fluid
    Set ICEM_FluidAndBOI.Extract_Surface_Symm = Surface_Symm
    
End Function


'*****************************
'ICEM_Subline_01
'*****************************
Function ICEM_Subline_01(ByVal DocumentObject As Object, _
                         ByRef Entity_GenWing_WithTrail As Type_GenWing_WithTrail, ByRef Entity_SmoothAndJoint As Type_SmoothAndJoint, _
                         ByVal Data_SectionPoint As Variant, ByVal Num_Section As Integer, ByVal Num_PointPerSpline As Integer, _
                         ByVal MAC_Length As Double, ByVal MAC_x As Double, _
                         ByVal Diameter_Fillet As Double, ByVal Rate_Fluid As Double, _
                         ByVal Index_NonActSection_ICEM As Variant) _
                         As Type_ICEM_Subline_01
   
    'CreateOrderGeometry
    Set WorkObject = DocumentObject.Part.OrderedGeometricalSets.Add()
    DocumentObject.Part.OrderedGeometricalSets.Item(5).Name = "ICEM_Subline_01"
    
    
    Set DPH = DocumentObject.Part.HybridShapeFactory
    
    Num_Spline = Num_Section * 2
    Num_Divide = 11
    Num_Span = Num_Section * 3 - 2

    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    Deviation_Bridge = Entity_SmoothAndJoint.Deviation_Bridge
    
    
    '-----------------------------------
    'Create Direction_Dihedral
    '-----------------------------------
    Dim Data_QuaterPoint(1 To MaxNum_Array, 1 To 3) As Double
    Dim Dihedral(1 To MaxNum_Array) As Double
    Dim Direction_Dihedral(1 To MaxNum_Array) As Object
    
    
    'Solve Dihedral
    Dihedral(1) = 0
    
    For nSection = 1 To Num_Section
        
        X1_Lead = Data_SectionPoint((nSection - 1) * Num_PointPerSpline + 1, 1)
        Y1_Lead = Data_SectionPoint((nSection - 1) * Num_PointPerSpline + 1, 2)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Y1_Trail = (Data_SectionPoint(nSection * Num_PointPerSpline, 2) + Data_SectionPoint((Num_Spline - nSection + 1) * Num_PointPerSpline, 2)) / 2
        Z1_Trail = (Data_SectionPoint(nSection * Num_PointPerSpline, 3) + Data_SectionPoint((Num_Spline - nSection + 1) * Num_PointPerSpline, 3)) / 2
        
        Dx = X1_Trail - X1_Lead
        Dy = Y1_Trail - Y1_Lead
        Dz = Z1_Trail - Z1_Lead
        
        Data_QuaterPoint(nSection, 1) = X1_Lead + Dx / 4
        Data_QuaterPoint(nSection, 2) = Y1_Lead + Dy / 4
        Data_QuaterPoint(nSection, 3) = Z1_Lead + Dz / 4
                
    Next nSection
    
    For nSection = 2 To Num_Section - 1

        Dz = Data_QuaterPoint(nSection, 3) - Data_QuaterPoint(nSection - 1, 3)
        Dy = Data_QuaterPoint(nSection, 2) - Data_QuaterPoint(nSection - 1, 2)

        Dihedral_Inner = Atn(Dz / Dy) * 180 / Pi
        
        Dz = Data_QuaterPoint(nSection + 1, 3) - Data_QuaterPoint(nSection, 3)
        Dy = Data_QuaterPoint(nSection + 1, 2) - Data_QuaterPoint(nSection, 2)

        Dihedral_Outer = Atn(Dz / Dy) * 180 / Pi
        
        Dihedral(1 + (nSection - 2) * 3 + 1) = Dihedral_Inner
        Dihedral(1 + (nSection - 2) * 3 + 2) = Dihedral_Inner
        Dihedral(1 + (nSection - 2) * 3 + 3) = (Dihedral_Inner + Dihedral_Outer) / 2

    Next nSection
    
    Dihedral(1 + (Num_Section - 2) * 3 + 1) = Dihedral_Outer
    Dihedral(1 + (Num_Section - 2) * 3 + 2) = Dihedral_Outer
    Dihedral(1 + (Num_Section - 2) * 3 + 3) = Dihedral_Outer


    'Create Direction
    For nSpan = 1 To Num_Span
        
        nSection = Int(nSpan / 3) + 1
    
        Set Direction_Line_Point = DPH.AddNewPointOnCurveFromPercent(Entity_SmoothAndJoint.Spline_UpLow(nSection), 0, False)
        
        Set Direction_Line = DPH.AddNewLineAngle(Direction_Z, PLANE_YZ, Direction_Line_Point, False, 0, 0.1 * MAC_Length, Dihedral(nSpan), True)
        
        'WorkObject.InsertHybridShape Direction_Line
        
        Set Direction_Dihedral(nSpan) = DPH.AddNewDirection(Direction_Line)
        
    Next nSpan
    
    
    '-----------------------------------
    'Define
    '-----------------------------------
    Set Extract_Cache = DPH.AddNewExtractMulti(EmptyObject)
    WorkObject.InsertHybridShape Extract_Cache
    
    
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
       
       
    'Angle_Tip_Lead & Trail
    X1 = (Data_SectionPoint(Num_Section * Num_PointPerSpline, 1) + Data_SectionPoint((Num_Spline - Num_Section + 1) * Num_PointPerSpline, 1)) / 2
    Y1 = (Data_SectionPoint(Num_Section * Num_PointPerSpline, 2) + Data_SectionPoint((Num_Spline - Num_Section + 1) * Num_PointPerSpline, 2)) / 2
    Z1 = (Data_SectionPoint(Num_Section * Num_PointPerSpline, 3) + Data_SectionPoint((Num_Spline - Num_Section + 1) * Num_PointPerSpline, 3)) / 2
    
    Set Point_1 = DPH.AddNewPointCoord(X1, Y1, Z1)
    
    X1 = Data_SectionPoint((Num_Section - 1) * Num_PointPerSpline + 1, 1)
    Y1 = Data_SectionPoint((Num_Section - 1) * Num_PointPerSpline + 1, 2)
    Z1 = Data_SectionPoint((Num_Section - 1) * Num_PointPerSpline + 1, 3)
    
    Set Point_2 = DPH.AddNewPointCoord(X1, Y1, Z1)
    
    X1 = (Data_SectionPoint((Num_Section - 1) * Num_PointPerSpline, 1) + Data_SectionPoint((Num_Spline - (Num_Section - 1) + 1) * Num_PointPerSpline, 1)) / 2
    Y1 = (Data_SectionPoint((Num_Section - 1) * Num_PointPerSpline, 2) + Data_SectionPoint((Num_Spline - (Num_Section - 1) + 1) * Num_PointPerSpline, 2)) / 2
    Z1 = (Data_SectionPoint((Num_Section - 1) * Num_PointPerSpline, 3) + Data_SectionPoint((Num_Spline - (Num_Section - 1) + 1) * Num_PointPerSpline, 3)) / 2
    
    Set Point_3 = DPH.AddNewPointCoord(X1, Y1, Z1)
    
    Set Line_1 = DPH.AddNewLinePtPt(Point_1, Point_2)
    Set Line_2 = DPH.AddNewLinePtPt(Point_1, Point_3)
    
    Angle_Tip_Trail = GetAngle(Line_1, Line_2, DocumentObject, Extract_Cache)
    
    
    X1 = (Data_SectionPoint((Num_Section - 1) * Num_PointPerSpline, 1) + Data_SectionPoint((Num_Spline - (Num_Section - 1) + 1) * Num_PointPerSpline, 1)) / 2
    X2 = (Data_SectionPoint(Num_Section * Num_PointPerSpline, 1) + Data_SectionPoint((Num_Spline - Num_Section + 1) * Num_PointPerSpline, 1)) / 2
    
    If X1 > X2 Then
        Angle_Tip_Trail = 180 - Angle_Tip_Trail
    End If
    
    
    X1 = Data_SectionPoint((Num_Section - 1) * Num_PointPerSpline + 1, 1)
    Y1 = Data_SectionPoint((Num_Section - 1) * Num_PointPerSpline + 1, 2)
    Z1 = Data_SectionPoint((Num_Section - 1) * Num_PointPerSpline + 1, 3)
    
    Set Point_1 = DPH.AddNewPointCoord(X1, Y1, Z1)
    
    X1 = (Data_SectionPoint(Num_Section * Num_PointPerSpline, 1) + Data_SectionPoint((Num_Spline - Num_Section + 1) * Num_PointPerSpline, 1)) / 2
    Y1 = (Data_SectionPoint(Num_Section * Num_PointPerSpline, 2) + Data_SectionPoint((Num_Spline - Num_Section + 1) * Num_PointPerSpline, 2)) / 2
    Z1 = (Data_SectionPoint(Num_Section * Num_PointPerSpline, 3) + Data_SectionPoint((Num_Spline - Num_Section + 1) * Num_PointPerSpline, 3)) / 2
    
    Set Point_2 = DPH.AddNewPointCoord(X1, Y1, Z1)
    
    X1 = Data_SectionPoint((Num_Section - 2) * Num_PointPerSpline + 1, 1)
    Y1 = Data_SectionPoint((Num_Section - 2) * Num_PointPerSpline + 1, 2)
    Z1 = Data_SectionPoint((Num_Section - 2) * Num_PointPerSpline + 1, 3)
    
    Set Point_3 = DPH.AddNewPointCoord(X1, Y1, Z1)
    
    Set Line_1 = DPH.AddNewLinePtPt(Point_1, Point_2)
    Set Line_2 = DPH.AddNewLinePtPt(Point_1, Point_3)
    
    Angle_Tip_Lead = GetAngle(Line_1, Line_2, DocumentObject, Extract_Cache)
    
    X1 = Data_SectionPoint((Num_Section - 2) * Num_PointPerSpline + 1, 1)
    X2 = Data_SectionPoint((Num_Section - 1) * Num_PointPerSpline + 1, 1)
    
    If X1 < X2 Then
        Angle_Tip_Lead = 180 - Angle_Tip_Lead
    End If
    
    
    'Divide
    Dim Divide(1 To MaxNum_Array, 1 To 11) As Double
    
    For nSpan = 1 To Num_Span
        
        Divide(nSpan, 1) = 0
        
        For nDivide = 2 To 9
            
            x0 = (nDivide - 2) / 8
            
            'y0 = 1 - Cos(x0 * Pi)
            'y0 = y0 / 2
            
            K = 1.3
            y0 = -(1 - Cos((1 - x0) * Pi)) ^ K + 2 ^ K
            y0 = y0 / (2 ^ K)
            
            Divide(nSpan, nDivide) = 0.03 + 0.97 * y0

        Next nDivide
        
        Divide(nSpan, 10) = 999
        Divide(nSpan, 11) = 1
        
    Next nSpan
    
    
    'Span_BlockSection
    Dim Span_BlockSection(1 To MaxNum_Array) As Double
    
    Span_BlockSection(1) = 0
    Span_BlockSection(2) = Entity_SmoothAndJoint.Length_Offset_Outside(1) * 0.99
    
    For nSection = 2 To Num_Section - 1
    
        Span_BlockSection(2 + (nSection - 2) * 3 + 1) = Data_SectionPoint(Num_PointPerSpline * (nSection - 1) + 1, 2) - Entity_SmoothAndJoint.Length_Offset_Inside(nSection) * 0.99
        Span_BlockSection(2 + (nSection - 2) * 3 + 2) = Data_SectionPoint(Num_PointPerSpline * (nSection - 1) + 1, 2)
        Span_BlockSection(2 + (nSection - 2) * 3 + 3) = Data_SectionPoint(Num_PointPerSpline * (nSection - 1) + 1, 2) + Entity_SmoothAndJoint.Length_Offset_Outside(nSection) * 0.99
        
    Next nSection
    
    Span_BlockSection(Num_Span - 1) = 999
    
    Span_BlockSection(Num_Span) = Data_SectionPoint(Num_PointPerSpline * (Num_Section - 1) + 1, 2)
    
    
    'SpanSLength_BlockSection
    Dim SpanSLength_BlockSection(1 To MaxNum_Array) As Double
    
    SpanSLength_BlockSection(1) = 0
    
    For nSpan = 2 To Num_Span
        
        nSection = Int((nSpan - 2) / 3) + 1
        
        nSpan_Init = (nSection - 1) * 3 + 1
            
        SpanSLength_BlockSection(nSpan) = SpanSLength_BlockSection(nSpan_Init) + (Span_BlockSection(nSpan) - Span_BlockSection(nSpan_Init)) / Cos(Dihedral(nSpan) / 57.3)
        
    Next nSpan
    
    
    Set Point_1 = DPH.AddNewPointOnCurveFromPercent(Entity_GenWing_WithTrail.Spline_UpLow(Num_Section), Divide(Num_Span, 2), False)
    Set Point_2 = DPH.AddNewPointOnCurveFromPercent(Entity_GenWing_WithTrail.Spline_UpLow(Num_Section), Divide(Num_Span, 3), False)

    Distance = GetDistance(Point_1, Point_2, DocumentObject, Extract_Cache)
    
    Length_1 = Distance * 2
    Length_2 = SpanSLength_BlockSection(Num_Span) / 35
    
    If Length_1 > Length_2 Then
        Length_Offset_Tip = Length_1
    Else
        Length_Offset_Tip = Length_2
    End If
    
    Span_BlockSection(Num_Span - 1) = Span_BlockSection(Num_Span) - Length_Offset_Tip * Cos(Dihedral(Num_Span) / 57.3)
    
    SpanSLength_BlockSection(Num_Span - 1) = SpanSLength_BlockSection(Num_Span) - Length_Offset_Tip
    

    'LayerHeight
    Dim LayerHeight(1 To MaxNum_Array) As Double
    
    For nSection = 1 To Num_Section
    
        If Length_Chord(nSection) >= MAC_Length Then
        
            LayerHeight(nSection) = Length_Chord(nSection) * 0.05
            
        Else
            
            Length_1 = (Length_Chord(nSection) * 0.05 + MAC_Length * 0.05) / 2
            
            Length_2 = Length_Chord(nSection) * 0.2
            
            If Length_1 <= Length_2 Then
                LayerHeight(nSection) = Length_1
            Else
                LayerHeight(nSection) = Length_2
            End If
            
        End If
        
    Next nSection
    
    
    'LayerHeight_BlockSection
    Dim LayerHeight_BlockSection(1 To MaxNum_Array) As Double
    
    Dim Index_Basic(1 To MaxNum_Array) As Integer
    Dim Index_Inner(1 To MaxNum_Array) As Integer
    Dim Index_Outer(1 To MaxNum_Array) As Integer
    
    For nSection = 1 To Num_Section

        LayerHeight_BlockSection((nSection - 1) * 3 + 1) = LayerHeight(nSection)
        
    Next nSection
    
    For nSection = 1 To Num_Section - 1
    
        Index_Basic(nSection) = (nSection - 1) * 3 + 2
        Index_Inner(nSection) = (nSection - 1) * 3 + 1
        Index_Outer(nSection) = (nSection - 1) * 3 + 4
    
    Next nSection
     
    For i = 1 To Num_Section - 1
        
        LayerHeight_BlockSection(Index_Basic(i)) = LayerHeight_BlockSection(Index_Inner(i)) + (Span_BlockSection(Index_Basic(i)) - Span_BlockSection(Index_Inner(i))) / _
                                                                                              (Span_BlockSection(Index_Outer(i)) - Span_BlockSection(Index_Inner(i))) * _
                                                                                              (LayerHeight_BlockSection(Index_Outer(i)) - LayerHeight_BlockSection(Index_Inner(i)))
        
        LayerHeight_BlockSection(Index_Basic(i) + 1) = LayerHeight_BlockSection(Index_Inner(i)) + (Span_BlockSection(Index_Basic(i) + 1) - Span_BlockSection(Index_Inner(i))) / _
                                                                                                  (Span_BlockSection(Index_Outer(i)) - Span_BlockSection(Index_Inner(i))) * _
                                                                                                  (LayerHeight_BlockSection(Index_Outer(i)) - LayerHeight_BlockSection(Index_Inner(i)))
        
    Next i
    
    
    'Length_Chord_BlockSection
    Dim Length_Chord_BlockSection(1 To MaxNum_Array) As Double
    
    For nSection = 1 To Num_Section
        
        Length_Chord_BlockSection((nSection - 1) * 3 + 1) = Length_Chord(nSection)
        
    Next nSection
    
    For nSection = 1 To Num_Section - 1
    
        Index_Basic(nSection) = (nSection - 1) * 3 + 2
        Index_Inner(nSection) = (nSection - 1) * 3 + 1
        Index_Outer(nSection) = (nSection - 1) * 3 + 4
    
    Next nSection
    
    For i = 1 To Num_Section - 1
        
        Length_Chord_BlockSection(Index_Basic(i)) = Length_Chord_BlockSection(Index_Inner(i)) + (Span_BlockSection(Index_Basic(i)) - Span_BlockSection(Index_Inner(i))) / _
                                                                                                (Span_BlockSection(Index_Outer(i)) - Span_BlockSection(Index_Inner(i))) * _
                                                                                                (Length_Chord_BlockSection(Index_Outer(i)) - Length_Chord_BlockSection(Index_Inner(i)))
        
        Length_Chord_BlockSection(Index_Basic(i) + 1) = Length_Chord_BlockSection(Index_Inner(i)) + (Span_BlockSection(Index_Basic(i) + 1) - Span_BlockSection(Index_Inner(i))) / _
                                                                                                    (Span_BlockSection(Index_Outer(i)) - Span_BlockSection(Index_Inner(i))) * _
                                                                                                    (Length_Chord_BlockSection(Index_Outer(i)) - Length_Chord_BlockSection(Index_Inner(i)))
        
    Next i
    
    
    'Hide
    DocumentObject.Selection.Add Extract_Cache
    DocumentObject.Selection.VisProperties.SetShow 1
    DocumentObject.Selection.Clear
   
        
'-----------------------------------
'Deal Main
'-----------------------------------
    
    '-----------------------------------
    'Create Spline_SectionProject
    '-----------------------------------
    Dim Line_Guide_Total(1 To MaxNum_Array) As Object
    
    Dim Orientation_Spline_SectionProject_Fillet_z_ForSplit(1 To MaxNum_Array) As Integer
     
    Dim Spline_SectionProject_UpLow(1 To MaxNum_Array, 1 To 2) As Object
    Dim Spline_SectionProject_Fillet(1 To MaxNum_Array) As Object
    Dim Spline_SectionProject(1 To MaxNum_Array, 1 To 2) As Object
    
    
    Set Extract_Cache = DPH.AddNewExtractMulti(EmptyObject)
    WorkObject.InsertHybridShape Extract_Cache

        
    'Create Line_Guide_Total
    For i = 1 To 4
    
        Set Line_Guide_Total(i) = DPH.AddNewJoin(Entity_GenWing_WithTrail.Line_Guide(1, i), Entity_GenWing_WithTrail.Line_Guide(2, i))
        
        For nSection = 3 To Num_Section - 1
            Line_Guide_Total(i).AddElement Entity_GenWing_WithTrail.Line_Guide(nSection, i)
        Next nSection
        
    Next i
    
    
    'Create Spline_SectionProject
    For nSpan = 1 To Num_Span
        
        'Line_ToProject
        If nSpan < Num_Span - 1 Then
            
            X1 = 0
            Y1 = Span_BlockSection(nSpan)
            Z1 = 0
            
            Set Point_1 = DPH.AddNewPointCoord(X1, Y1, Z1)
            
            Set Line_1 = DPH.AddNewLinePtDir(Point_1, Direction_X, -10 * MAC_Length, 10 * MAC_Length, False)
            
            Set Surface_1 = DPH.AddNewExtrude(Line_1, 10 * MAC_Length, 10 * MAC_Length, Direction_Z)
            
            
            Set Point_1 = DPH.AddNewIntersection(Surface_1, Line_Guide_Total(1))
            Set Point_2 = DPH.AddNewIntersection(Surface_1, Line_Guide_Total(3))
        
        ElseIf nSpan = Num_Span - 1 Then
            
            X1 = Data_SectionPoint((Num_Section - 2) * Num_PointPerSpline + 1, 1)
            Y1 = Data_SectionPoint((Num_Section - 2) * Num_PointPerSpline + 1, 2)
            Z1 = Data_SectionPoint((Num_Section - 2) * Num_PointPerSpline + 1, 3)
            
            Set Point_1 = DPH.AddNewPointCoord(X1, Y1, Z1)
            
            X1 = Data_SectionPoint((Num_Section - 1) * Num_PointPerSpline + 1, 1)
            Y1 = Data_SectionPoint((Num_Section - 1) * Num_PointPerSpline + 1, 2)
            Z1 = Data_SectionPoint((Num_Section - 1) * Num_PointPerSpline + 1, 3)
            
            Set Point_2 = DPH.AddNewPointCoord(X1, Y1, Z1)
            
            Set Line_1 = DPH.AddNewLinePtPt(Point_1, Point_2)
    
            Set Direction_1 = DPH.AddNewDirection(Line_1)
            'Set Direction_1 = DPH.AddNewDirection(Entity_GenWing_WithTrail.Line_Guide(Num_Section - 1, 1))
            
            
            Set Flat_Surface_Tip_Fill = DPH.AddNewPlaneOffset(Entity_SmoothAndJoint.Surface_Tip_Fill, 0, False)
            
            Set Flat_ToIntersection = DPH.AddNewEmptyTranslate()
            Flat_ToIntersection.ElemToTranslate = Flat_Surface_Tip_Fill
            Flat_ToIntersection.VectorType = 0
            Flat_ToIntersection.Direction = Direction_1
            Flat_ToIntersection.DistanceValue = -Length_Offset_Tip
            Flat_ToIntersection.VolumeResult = False
            
            Set Point_1 = DPH.AddNewIntersection(Flat_ToIntersection, Entity_GenWing_WithTrail.Line_Guide(Num_Section - 1, 1))
            Set Point_2 = DPH.AddNewIntersection(Flat_ToIntersection, Entity_GenWing_WithTrail.Line_Guide(Num_Section - 1, 3))

        End If
        
        
        If nSpan <= Num_Span - 1 Then
        
            Set Line_ToProject = DPH.AddNewLinePtPt(Point_1, Point_2)
            
            Set Line_ToProject = DPH.AddNewExtrapolLength(Point_1, Line_ToProject, 10 * Diameter_Fillet)
            Line_ToProject.BorderType = 1
            Line_ToProject.SetAssemble True
            Line_ToProject.SetContinuityType 1, 1
            
            Set Line_ToProject = DPH.AddNewExtrapolLength(Point_2, Line_ToProject, 10 * Diameter_Fillet)
            Line_ToProject.BorderType = 1
            Line_ToProject.SetAssemble True
            Line_ToProject.SetContinuityType 1, 1
            
            'WorkObject.InsertHybridShape Line_ToProject
        
        End If


        'Project
        If nSpan <= Num_Span - 1 Then
            
            Set Direction_Project = Direction_Dihedral(nSpan)

            Set Spline_SectionProject_UpLow(nSpan, 1) = DPH.AddNewProject(Line_ToProject, Entity_SmoothAndJoint.Surface_Joint_UpLow_Low)
            Spline_SectionProject_UpLow(nSpan, 1).Normal = False
            Spline_SectionProject_UpLow(nSpan, 1).Direction = Direction_Project

            Set Spline_SectionProject_UpLow(nSpan, 2) = DPH.AddNewProject(Line_ToProject, Entity_SmoothAndJoint.Surface_Joint_UpLow_Up)
            Spline_SectionProject_UpLow(nSpan, 2).Normal = False
            Spline_SectionProject_UpLow(nSpan, 2).Direction = Direction_Project
            
            If nSpan = 1 Then
            
                Set Spline_SectionProject_Fillet(nSpan) = DPH.AddNewIntersection(Entity_SmoothAndJoint.Surface_Joint_Fillet, PLANE_ZX)
            
            Else
                
                Set Spline_SectionProject_Fillet(nSpan) = DPH.AddNewProject(Line_ToProject, Entity_SmoothAndJoint.Surface_Joint_Fillet)
                Spline_SectionProject_Fillet(nSpan).Normal = False
                Spline_SectionProject_Fillet(nSpan).Direction = Direction_Project
            
            End If

        ElseIf nSpan = Num_Span Then
            
            Set Spline_SectionProject_UpLow(nSpan, 1) = Entity_SmoothAndJoint.Spline_UpLow(Num_Section + 1)
            
            Set Spline_SectionProject_UpLow(nSpan, 2) = Entity_SmoothAndJoint.Spline_UpLow(Num_Section)
            
            Set Spline_SectionProject_Fillet(nSpan) = Entity_SmoothAndJoint.Spline_Fillet(Num_Section)
            
        End If
                
        'WorkObject.InsertHybridShape Spline_SectionProject_UpLow(nSpan, 1)
        'WorkObject.InsertHybridShape Spline_SectionProject_UpLow(nSpan, 2)
        'WorkObject.InsertHybridShape Spline_SectionProject_Fillet(nSpan)


        'Split And Combine
        Set Point_1 = DPH.AddNewPointOnCurveFromPercent(Spline_SectionProject_Fillet(nSpan), 0.5, False)

        Orientation_Spline_SectionProject_Fillet_z_ForSplit(nSpan) = Orientation_ForSplit_ByZ(Spline_SectionProject_Fillet(nSpan), Point_1, DocumentObject, Extract_Cache)

        Set Spline_Fillet_Low = DPH.AddNewHybridSplit(Spline_SectionProject_Fillet(nSpan), Point_1, Orientation_Spline_SectionProject_Fillet_z_ForSplit(nSpan))
        Set Spline_Fillet_Up = DPH.AddNewHybridSplit(Spline_SectionProject_Fillet(nSpan), Point_1, -Orientation_Spline_SectionProject_Fillet_z_ForSplit(nSpan))

        Set Spline_SectionProject(nSpan, 1) = DPH.AddNewJoin(Spline_SectionProject_UpLow(nSpan, 1), Spline_Fillet_Low)
        Set Spline_SectionProject(nSpan, 2) = DPH.AddNewJoin(Spline_SectionProject_UpLow(nSpan, 2), Spline_Fillet_Up)

        'WorkObject.InsertHybridShape Spline_SectionProject(nSpan, 1)
        'WorkObject.InsertHybridShape Spline_SectionProject(nSpan, 2)

    Next nSpan
    
    
    'Hide
    DocumentObject.Selection.Add Extract_Cache
    DocumentObject.Selection.VisProperties.SetShow 1
    DocumentObject.Selection.Clear
        
        
    '-----------------------------------
    'Change Spline_SectionProject
    '-----------------------------------
    Dim Orientation_Spline_SectionProject_UpLow_x_ForSplit(1 To MaxNum_Array, 1 To 2)
    Dim Orientation_Spline_SectionProject_x_ForSplit(1 To MaxNum_Array, 1 To 2) As Integer
    Dim Orientation_LeadPoint(1 To MaxNum_Array) As Integer
    
    Dim Distance_LeadPoint(1 To MaxNum_Array) As Double
        
    For nSpan = 1 To Num_Span
        
        Set Extract_Cache = DPH.AddNewExtractMulti(EmptyObject)
        WorkObject.InsertHybridShape Extract_Cache

        Orientation = Orientation_ForPercent_ByX(Spline_SectionProject(nSpan, 1), DocumentObject, Extract_Cache)
        
        Set Point_Lead_Ref = DPH.AddNewPointOnCurveFromPercent(Spline_SectionProject(nSpan, 1), 0, Orientation)

        Set Point_Trail = DPH.AddNewPointOnCurveFromPercent(Spline_SectionProject(nSpan, 1), 1, Orientation)


        Extract_Cache.AddConstraintTolerant Point_Lead_Ref, 3, False, False, 0.1, 0.5, 0.98, 1
        Extract_Cache.SetElement 1, Point_Lead_Ref

        Extract_Cache.AddConstraintTolerant Point_Trail, 3, False, False, 0.1, 0.5, 0.98, 1
        Extract_Cache.SetElement 1, Point_Trail
        DocumentObject.Part.Update

        Point_Lead_Ref.GetCoordinates XYZ_Cache
        Z0 = XYZ_Cache(2)

    
        'Solve Point_Lead
        Set Spline_SectionProject_Total = DPH.AddNewJoin(Spline_SectionProject(nSpan, 1), Spline_SectionProject(nSpan, 2))
        
        
        Set Flat_0 = DPH.AddNewPlaneOffsetPt(PLANE_YZ, Point_Lead_Ref)
        Set Flat_1 = DPH.AddNewPlaneOffset(Flat_0, Length_Chord_BlockSection(nSpan) * 0.005, False)
        Set Flat_2 = DPH.AddNewPlaneOffset(Flat_0, Length_Chord_BlockSection(nSpan) * 0.02, False)
        
        Set Point_1_Low = DPH.AddNewIntersection(Spline_SectionProject(nSpan, 1), Flat_1)
        Set Point_2_Low = DPH.AddNewIntersection(Spline_SectionProject(nSpan, 1), Flat_2)
        
        Set Point_1_Up = DPH.AddNewIntersection(Spline_SectionProject(nSpan, 2), Flat_1)
        Set Point_2_Up = DPH.AddNewIntersection(Spline_SectionProject(nSpan, 2), Flat_2)
        
        Set Line_1 = DPH.AddNewLinePtPt(Point_1_Low, Point_1_Up)
        Set Line_2 = DPH.AddNewLinePtPt(Point_2_Low, Point_2_Up)
        
        Set Point_1_Mid = DPH.AddNewPointOnCurveFromPercent(Line_1, 0.5, False)
        Set Point_2_Mid = DPH.AddNewPointOnCurveFromPercent(Line_2, 0.5, False)
        
        Set Line_Direction = DPH.AddNewLinePtPt(Point_1_Mid, Point_2_Mid)
        
        Set Direction_1 = DPH.AddNewDirection(Line_Direction)
        
        
        Set Point_Lead = DPH.AddNewExtremum(Spline_SectionProject_Total, Direction_1, 0)

        Set Point_Lead = DPH.AddNewNear(Point_Lead, Point_Lead_Ref)

        Set Point_Lead = DPH.AddNewPointOnCurveWithReferenceFromDistance(Spline_SectionProject_Total, Point_Lead, 0, Orientation)


        Extract_Cache.AddConstraintTolerant Point_Lead, 3, False, False, 0.1, 0.5, 0.98, 1
        Extract_Cache.SetElement 1, Point_Lead
        DocumentObject.Part.Update

        Point_Lead.GetCoordinates XYZ_Cache
        Z2 = XYZ_Cache(2)


        If Z2 > Z0 Then
            Orientation = True
        Else
            Orientation = False
        End If

        K = 0.0001
        Length_Offset = Length_Chord_BlockSection(nSpan) * K

        If Length_Offset < 0.022 Then
            Length_Offset = 0.022
        End If
        
        If nSpan <> Num_Span - 1 And nSpan <> Num_Span Then
        
            Set Point_Lead = DPH.AddNewPointOnCurveWithReferenceFromDistance(Spline_SectionProject_Total, Point_Lead, Length_Offset, Orientation)
            
        End If

        
        Extract_Cache.AddConstraintTolerant Point_Lead, 3, False, False, 0.1, 0.5, 0.98, 1
        Extract_Cache.SetElement 1, Point_Lead
        DocumentObject.Part.Update

        Point_Lead.GetCoordinates XYZ_Cache
        Z1 = XYZ_Cache(2)

        
        'Split And Combine
        For nDu = 1 To 2
            
            Set Point_1 = DPH.AddNewPointOnCurveFromPercent(Spline_SectionProject_UpLow(nSpan, nDu), 0.5, False)
                            
            Orientation_Spline_SectionProject_UpLow_x_ForSplit(nSpan, nDu) = Orientation_ForSplit_ByX(Spline_SectionProject_UpLow(nSpan, nDu), Point_1, DocumentObject, Extract_Cache)
            
        Next nDu
        
        
        For nDu = 1 To 2
            
            Set Point_1 = DPH.AddNewPointOnCurveFromPercent(Spline_SectionProject(nSpan, nDu), 0.5, False)

            Orientation_Spline_SectionProject_x_ForSplit(nSpan, nDu) = Orientation_ForSplit_ByX(Spline_SectionProject(nSpan, nDu), Point_1, DocumentObject, Extract_Cache)
            
        Next nDu
            
            
        If Abs(Z1 - Z0) > 0.001 Then
            If Z1 < Z0 Then
                Orientation_LeadPoint(nSpan) = -1
                Index_1 = 1
                Index_2 = 2
            Else
                Orientation_LeadPoint(nSpan) = 1
                Index_1 = 2
                Index_2 = 1
            End If
        Else
            Orientation_LeadPoint(nSpan) = 0
        End If
        
            
        If Orientation_LeadPoint(nSpan) <> 0 Then
        
            Set Spline_1 = DPH.AddNewHybridSplit(Spline_SectionProject_UpLow(nSpan, Index_1), Point_Lead, Orientation_Spline_SectionProject_UpLow_x_ForSplit(nSpan, Index_1))
            
            Set Spline_SectionProject_UpLow(nSpan, Index_1) = DPH.AddNewHybridSplit(Spline_SectionProject_UpLow(nSpan, Index_1), Point_Lead, -Orientation_Spline_SectionProject_UpLow_x_ForSplit(nSpan, Index_1))
            
            Set Spline_SectionProject_UpLow(nSpan, Index_2) = DPH.AddNewJoin(Spline_SectionProject_UpLow(nSpan, Index_2), Spline_1)
            
            
            Set M = DocumentObject.GetWorkbench("SPAWorkbench").GetMeasurable(Point_Lead)
            Distance_LeadPoint(nSpan) = M.GetMinimumDistance(Spline_SectionProject(nSpan, Index_2))
            
            
            Set Spline_1 = DPH.AddNewHybridSplit(Spline_SectionProject(nSpan, Index_1), Point_Lead, Orientation_Spline_SectionProject_x_ForSplit(nSpan, Index_1))
            
            Set Spline_SectionProject(nSpan, Index_1) = DPH.AddNewHybridSplit(Spline_SectionProject(nSpan, Index_1), Point_Lead, -Orientation_Spline_SectionProject_x_ForSplit(nSpan, Index_1))
            
            Set Spline_SectionProject(nSpan, Index_2) = DPH.AddNewJoin(Spline_SectionProject(nSpan, Index_2), Spline_1)
        
        End If
        
        
        'Hide
        DocumentObject.Selection.Add Extract_Cache
        DocumentObject.Selection.VisProperties.SetShow 1
        DocumentObject.Selection.Clear
    
    Next nSpan

    
    '-----------------------------------
    'Create Line_NormalVector
    '-----------------------------------
    Dim Orientation_Spline_SectionProject_UpLow_x_ForPercent(1 To MaxNum_Array, 1 To 2) As Boolean
    Dim Orientation_Line_NormalVector_Root_ForPercent(1 To MaxNum_Array) As Boolean
    Dim Orientation_FaceVector(1 To MaxNum_Array) As Boolean
    
    Dim Line_NormalVector_Point(1 To MaxNum_Array, 1 To 2, 1 To 11) As Object
    Dim Line_NormalVector(1 To MaxNum_Array, 1 To 2, 1 To 11) As Object
    
    
    Set Extract_Cache = DPH.AddNewExtractMulti(EmptyObject)
    WorkObject.InsertHybridShape Extract_Cache
    
    
    'Solve Orientation_Spline_SectionProject_UpLow_x_ForPercent
    For nSpan = 1 To Num_Span
        For nDu = 1 To 2
            
            Orientation_Spline_SectionProject_UpLow_x_ForPercent(nSpan, nDu) = Orientation_ForPercent_ByX(Spline_SectionProject_UpLow(nSpan, nDu), DocumentObject, Extract_Cache)
            
        Next nDu
    Next nSpan
            
            
    'Create Line_NormalVector_Point
    Index_Separate = 2
    
    For nSpan = 1 To Num_Span
        For nDu = 1 To 2
            For nDivide = 1 To Index_Separate
                
                Orientation = Orientation_Spline_SectionProject_UpLow_x_ForPercent(nSpan, nDu)
        
                Set Line_NormalVector_Point(nSpan, nDu, nDivide) = DPH.AddNewPointOnCurveFromPercent(Spline_SectionProject_UpLow(nSpan, nDu), Divide(nSpan, nDivide), Orientation)
                
                'WorkObject.InsertHybridShape Line_NormalVector_Point(nSpan, nDU, nDivide)
                
            Next nDivide
        Next nDu
    Next nSpan
    
    
    For nBlock = 1 To Num_Section - 1
        For nDu = 1 To 2
            For nDivide = (Index_Separate + 1) To Num_Divide - 2
                
                nSpan_1 = (nBlock - 1) * 3 + 1
                nSpan_2 = nBlock * 3 + 1
                
                Orientation_1 = Orientation_Spline_SectionProject_UpLow_x_ForPercent(nSpan_1, nDu)
                Orientation_2 = Orientation_Spline_SectionProject_UpLow_x_ForPercent(nSpan_2, nDu)
                
                
                Set Point_1 = DPH.AddNewPointOnCurveFromPercent(Spline_SectionProject_UpLow(nSpan_1, nDu), Divide(nSpan_1, nDivide), Orientation_1)
                                                                
                Set Point_2 = DPH.AddNewPointOnCurveFromPercent(Spline_SectionProject_UpLow(nSpan_2, nDu), Divide(nSpan_2, nDivide), Orientation_2)
                
                Set Line_1 = DPH.AddNewLinePtPt(Point_1, Point_2)
                                    
                Set Surface_1 = DPH.AddNewExtrude(Line_1, 10 * MAC_Length, 10 * MAC_Length, Direction_Z)
                
                
                Set Line_NormalVector_Point(nSpan_1 + 1, nDu, nDivide) = DPH.AddNewIntersection(Surface_1, Spline_SectionProject_UpLow(nSpan_1 + 1, nDu))
                
                Set Line_NormalVector_Point(nSpan_2 - 1, nDu, nDivide) = DPH.AddNewIntersection(Surface_1, Spline_SectionProject_UpLow(nSpan_2 - 1, nDu))
                
            
                'WorkObject.InsertHybridShape Line_NormalVector_Point(nSpan_1 + 1, nDU, nDivide)
                'WorkObject.InsertHybridShape Line_NormalVector_Point(nSpan_2 - 1, nDU, nDivide)
                
            Next nDivide
        Next nDu
    Next nBlock
    
    For nBlock = 1 To Num_Section
        For nDu = 1 To 2
            For nDivide = (Index_Separate + 1) To Num_Divide - 2
                
                nSpan = (nBlock - 1) * 3 + 1
                
                Orientation = Orientation_Spline_SectionProject_UpLow_x_ForPercent(nSpan, nDu)

                Set Line_NormalVector_Point(nSpan, nDu, nDivide) = DPH.AddNewPointOnCurveFromPercent(Spline_SectionProject_UpLow(nSpan, nDu), Divide(nSpan, nDivide), Orientation)
                
                'WorkObject.InsertHybridShape Line_NormalVector_Point(nSpan, nDU, nDivide)
                
            Next nDivide
        Next nDu
    Next nBlock
    
    
    For nSpan = 1 To Num_Span
        For nDu = 1 To 2
            For nDivide = Num_Divide - 1 To Num_Divide
                
                If nDivide = Num_Divide - 1 Then
                    
                    If Orientation_Spline_SectionProject_Fillet_z_ForSplit(nSpan) = 1 Then
                        
                        Orientation = False
                        
                    ElseIf Orientation_Spline_SectionProject_Fillet_z_ForSplit(nSpan) = -1 Then
                    
                        Orientation = True
                    
                    End If
                    
                    If nDu = 1 Then
                        Set Line_NormalVector_Point(nSpan, nDu, nDivide) = DPH.AddNewPointOnCurveFromPercent(Spline_SectionProject_Fillet(nSpan), 0, Orientation)
                    Else
                        Set Line_NormalVector_Point(nSpan, nDu, nDivide) = DPH.AddNewPointOnCurveFromPercent(Spline_SectionProject_Fillet(nSpan), 1, Orientation)
                    End If
                
                ElseIf nDivide = Num_Divide Then
                
                    Set Line_NormalVector_Point(nSpan, nDu, nDivide) = DPH.AddNewPointOnCurveFromPercent(Spline_SectionProject_Fillet(nSpan), 0.5, False)
                    
                End If

                'WorkObject.InsertHybridShape Line_NormalVector_Point(nSpan, nDU, nDivide)

            Next nDivide
        Next nDu
    Next nSpan
       
       
    'Solve Orientation_NormalVector
    For nS = 1 To 3
    
        If nS = 1 Then
            Set Surface_1 = Entity_SmoothAndJoint.Surface_Joint_UpLow_Low
            Set Point_1 = Line_NormalVector_Point(4, 1, 4)
        ElseIf nS = 2 Then
            Set Surface_1 = Entity_SmoothAndJoint.Surface_Joint_UpLow_Up
            Set Point_1 = Line_NormalVector_Point(4, 2, 4)
        Else
            Set Surface_1 = Entity_SmoothAndJoint.Surface_Joint_Fillet
            Set Point_1 = Line_NormalVector_Point(4, 1, Num_Divide)
        End If
        
        
        Set Line_1 = DPH.AddNewLineNormal(Surface_1, Point_1, 0, LayerHeight_BlockSection(4), False)
        Set Line_2 = DPH.AddNewLineNormal(Surface_1, Point_1, 0, LayerHeight_BlockSection(4), True)
        
        Set Point_1 = DPH.AddNewPointOnCurveFromPercent(Line_1, 0.5, False)
        Set Point_2 = DPH.AddNewPointOnCurveFromPercent(Line_2, 0.5, False)
        
        Extract_Cache.AddConstraintTolerant Point_1, 3, False, False, 0.1, 0.5, 0.98, 1
        Extract_Cache.SetElement 1, Point_1
                    
        Extract_Cache.AddConstraintTolerant Point_2, 3, False, False, 0.1, 0.5, 0.98, 1
        Extract_Cache.SetElement 1, Point_2
        DocumentObject.Part.Update
        
        Point_1.GetCoordinates XYZ_Cache
        X1 = XYZ_Cache(0)
        Z1 = XYZ_Cache(2)
    
        Point_2.GetCoordinates XYZ_Cache
        X2 = XYZ_Cache(0)
        Z2 = XYZ_Cache(2)
        
        If nS = 1 Then
        
            If Z1 < Z2 Then
                Orientation_FaceVector(nS) = False
            Else
                Orientation_FaceVector(nS) = True
            End If
            
        ElseIf nS = 2 Then
        
            If Z1 > Z2 Then
                Orientation_FaceVector(nS) = False
            Else
                Orientation_FaceVector(nS) = True
            End If
            
        Else
        
            If X1 > X2 Then
                Orientation_FaceVector(nS) = False
            Else
                Orientation_FaceVector(nS) = True
            End If
            
        End If
            
    Next nS
    
    
    'Create Line_NormalVector
    For nSpan = 1 To Num_Span
        For nDu = 1 To 2
            For nDivide = 1 To Num_Divide
                
                If nDivide = 1 And Orientation_LeadPoint(nSpan) = -1 Then
                    nDU_Local = 1
                ElseIf nDivide = 1 And Orientation_LeadPoint(nSpan) = 1 Then
                    nDU_Local = 2
                Else
                    nDU_Local = nDu
                End If

                    
                If nDivide <> Num_Divide Then
                    If nDU_Local = 1 Then
                        Set Surface_1 = Entity_SmoothAndJoint.Surface_Joint_UpLow_Low
                        Orientation = Orientation_FaceVector(1)
                    Else
                        Set Surface_1 = Entity_SmoothAndJoint.Surface_Joint_UpLow_Up
                        Orientation = Orientation_FaceVector(2)
                    End If
                Else
                    Set Surface_1 = Entity_SmoothAndJoint.Surface_Joint_Fillet
                    Orientation = Orientation_FaceVector(3)
                End If
                
                Set Line_NormalVector(nSpan, nDu, nDivide) = DPH.AddNewLineNormal(Surface_1, Line_NormalVector_Point(nSpan, nDu, nDivide), 0, LayerHeight_BlockSection(nSpan), Orientation)
                
                
                If nSpan = 1 Then
                    
                    Set Line_NormalVector(nSpan, nDu, nDivide) = DPH.AddNewProject(Line_NormalVector(nSpan, nDu, nDivide), PLANE_ZX)
                    Line_NormalVector(nSpan, nDu, nDivide).Normal = False
                    Line_NormalVector(nSpan, nDu, nDivide).Direction = Direction_Y
                            
                End If
    
                'WorkObject.InsertHybridShape Line_NormalVector(nSpan, nDU, nDivide)
                    
            Next nDivide
        Next nDu
    Next nSpan
                
    
    'Hide
    DocumentObject.Selection.Add Extract_Cache
    DocumentObject.Selection.VisProperties.SetShow 1
    DocumentObject.Selection.Clear
    

    '-----------------------------------
    'Create Spline_SectionOffset
    '-----------------------------------
    Dim Spline_SectionOffset_Point(1 To MaxNum_Array, 1 To 2, 1 To 11, 1 To 2) As Object
    
    Dim Spline_SectionOffset_Lead(1 To MaxNum_Array, 1 To 2) As Object

    Dim Spline_SectionOffset_Mid(1 To MaxNum_Array, 1 To 2) As Object
    Dim Spline_SectionOffset_Mid_2(1 To MaxNum_Array, 1 To 2) As Object

    Dim Spline_SectionOffset_Trail_Total(1 To MaxNum_Array) As Object
    Dim Spline_SectionOffset_Trail(1 To MaxNum_Array, 1 To 2) As Object
    
    Dim Spline_SectionOffset(1 To MaxNum_Array, 1 To 2) As Object
        
    
    'Create Spline_SectionOffset_Point
    For nSpan = 1 To Num_Span
        For nDu = 1 To 2
            For nDivide = 1 To Num_Divide
                                    
                If nDivide = Num_Divide Then
                    Orientation = Orientation_FaceVector(3)
                Else
                    If nDu = 1 Then
                        Orientation = Orientation_FaceVector(1)
                    ElseIf nDu = 2 Then
                        Orientation = Orientation_FaceVector(2)
                    End If
                End If
                
                
                Set Spline_SectionOffset_Point(nSpan, nDu, nDivide, 1) = DPH.AddNewPointOnCurveFromPercent(Line_NormalVector(nSpan, nDu, nDivide), 0, Orientation)
                Set Spline_SectionOffset_Point(nSpan, nDu, nDivide, 2) = DPH.AddNewPointOnCurveFromPercent(Line_NormalVector(nSpan, nDu, nDivide), 1, Orientation)
                
                'WorkObject.InsertHybridShape Spline_SectionOffset_Point(nSpan, nDU, nDivide, 1)
                'WorkObject.InsertHybridShape Spline_SectionOffset_Point(nSpan, nDU, nDivide, 2)
            
            Next nDivide
        Next nDu
    Next nSpan
    
    
    'Create Spline_SectionOffset_Mid
    For nSpan = 1 To Num_Span
        For nDu = 1 To 2
        
            Set Spline_SectionOffset_Mid(nSpan, nDu) = DPH.AddNewSpline
        
            For nDivide = 3 To Num_Divide - 1
                
                If nDivide <> Num_Divide - 2 Then
                
                    Spline_SectionOffset_Mid(nSpan, nDu).AddPointWithConstraintExplicit Spline_SectionOffset_Point(nSpan, nDu, nDivide, 2), Nothing, -1#, 1, Nothing, 0#
                    
                End If

            Next nDivide
            
            'WorkObject.InsertHybridShape Spline_SectionOffset_Mid(nSpan, nDU)
            
                       
            Set Point_1 = Spline_SectionOffset_Point(nSpan, nDu, Num_Divide - 3, 2)

            Set Spline_SectionOffset_Mid_2(nSpan, nDu) = DPH.AddNewHybridSplit(Spline_SectionOffset_Mid(nSpan, nDu), Point_1, -1)
 
        Next nDu
    Next nSpan
    
    
    'Create Spline_SectionOffset_Lead
    For nSpan = 1 To Num_Span
        For nDu = 1 To 2
        
            If nDu = 1 Then
                Orientation = -1
            Else
                Orientation = 1
            End If
            
            
            Set Spline_SectionOffset_Lead(nSpan, nDu) = DPH.AddNewSpline
        
            Spline_SectionOffset_Lead(nSpan, nDu).AddPointWithConstraintFromCurve Spline_SectionOffset_Point(nSpan, nDu, 1, 2), Direction_Dihedral(nSpan), 1, Orientation, 1

            Spline_SectionOffset_Lead(nSpan, nDu).AddPointWithConstraintExplicit Spline_SectionOffset_Point(nSpan, nDu, 2, 2), Nothing, -1#, 1, Nothing, 0#
            
            Spline_SectionOffset_Lead(nSpan, nDu).AddPointWithConstraintFromCurve Spline_SectionOffset_Point(nSpan, nDu, 3, 2), Spline_SectionOffset_Mid(nSpan, nDu), 1, 1, 1
            
            'WorkObject.InsertHybridShape Spline_SectionOffset_Lead(nSpan, nDU)
                
        Next nDu
    Next nSpan
    
    
    'Create Spline_SectionOffset_Trail_Total
    For nSpan = 1 To Num_Span

        Set Spline_SectionOffset_Trail_Total(nSpan) = DPH.AddNewSpline
        
        Spline_SectionOffset_Trail_Total(nSpan).AddPointWithConstraintFromCurve Spline_SectionOffset_Point(nSpan, 1, Num_Divide - 1, 2), Spline_SectionOffset_Mid(nSpan, 1), 0.5, 1, 1
        
        Spline_SectionOffset_Trail_Total(nSpan).AddPointWithConstraintExplicit Spline_SectionOffset_Point(nSpan, 1, Num_Divide, 2), Nothing, -1#, -1, Nothing, 0#
        
        Spline_SectionOffset_Trail_Total(nSpan).AddPointWithConstraintFromCurve Spline_SectionOffset_Point(nSpan, 2, Num_Divide - 1, 2), Spline_SectionOffset_Mid(nSpan, 2), 0.5, -1, 1
        
        'WorkObject.InsertHybridShape Spline_SectionOffset_Trail_Total(nSpan)
            
    Next nSpan
    
    
    'Change Line_NormalVector And Spline_SectionOffset_Point
    For nSpan = 1 To Num_Span
        For nDu = 1 To 2
        
            Set Point_1 = Spline_SectionOffset_Point(nSpan, 1, Num_Divide, 1)
            Set Point_2 = DPH.AddNewPointOnCurveFromPercent(Spline_SectionOffset_Trail_Total(nSpan), 0.5, False)
            
            Set Line_1 = DPH.AddNewLinePtPt(Point_1, Point_2)
            
            Set Line_NormalVector(nSpan, nDu, Num_Divide) = Line_1
                
                
            Set Spline_SectionOffset_Point(nSpan, nDu, Num_Divide, 2) = Point_2
        
        Next nDu
    Next nSpan
    
    
    For nSpan = 1 To Num_Span
        For nDu = 1 To 2

            K = ((1 - Divide(nSpan, Num_Divide - 3)) - (1 - Divide(nSpan, Num_Divide - 2)) * 1) / (1 - Divide(nSpan, Num_Divide - 3))

            Set Point_1 = DPH.AddNewPointOnCurveFromPercent(Spline_SectionOffset_Mid_2(nSpan, nDu), K, False)

            Set Line_NormalVector(nSpan, nDu, Num_Divide - 2) = DPH.AddNewLinePtPt(Line_NormalVector_Point(nSpan, nDu, Num_Divide - 2), Point_1)
            
            
            Set Spline_SectionOffset_Point(nSpan, nDu, Num_Divide - 2, 2) = Point_1

        Next nDu
    Next nSpan
    
    
    'Create Spline_SectionOffset_Trail
    For nSpan = 1 To Num_Span

        Set Spline_SectionOffset_Trail(nSpan, 1) = DPH.AddNewHybridSplit(Spline_SectionOffset_Trail_Total(nSpan), Spline_SectionOffset_Point(nSpan, 1, Num_Divide, 2), 1)
        Set Spline_SectionOffset_Trail(nSpan, 2) = DPH.AddNewHybridSplit(Spline_SectionOffset_Trail_Total(nSpan), Spline_SectionOffset_Point(nSpan, 1, Num_Divide, 2), -1)

        'WorkObject.InsertHybridShape Spline_SectionOffset_Trail(nSpan, 1)
        'WorkObject.InsertHybridShape Spline_SectionOffset_Trail(nSpan, 2)

    Next nSpan
    
    
    'Combine
    For nSpan = 1 To Num_Span
        For nDu = 1 To 2
    
            Set Spline_SectionOffset(nSpan, nDu) = DPH.AddNewJoin(Spline_SectionOffset_Lead(nSpan, nDu), Spline_SectionOffset_Mid(nSpan, nDu))
            
            Spline_SectionOffset(nSpan, nDu).AddElement Spline_SectionOffset_Trail(nSpan, nDu)
                
                
            If nSpan = 1 Then
                    
                Set Spline_SectionOffset(nSpan, nDu) = DPH.AddNewProject(Spline_SectionOffset(nSpan, nDu), PLANE_ZX)
                Spline_SectionOffset(nSpan, nDu).Normal = False
                Spline_SectionOffset(nSpan, nDu).Direction = Direction_Y
                        
            End If
                
            'WorkObject.InsertHybridShape Spline_SectionOffset(nSpan, nDU)
        
        Next nDu
    Next nSpan
    
    
    '-----------------------------------
    'Create Spline_Span
    '-----------------------------------
    Dim Spline_SectionOffset_Point_Cache(1 To MaxNum_Array, 1 To 2, 1 To 11, 1 To 2) As Object
    Dim Spline_Span_Block(1 To 11, 1 To 2, 1 To 2, 1 To MaxNum_Array) As Object
    Dim Spline_Span(1 To 2, 1 To 11, 1 To 2) As Object
    
    Dim Point_MidFillet(1 To MaxNum_Array) As Object
    Dim Spline_Span_MidFillet_Block(1 To MaxNum_Array) As Object
    
    Dim Line_ToIntersect_Block(1 To MaxNum_Array) As Object
    
    
    Set Extract_Cache = DPH.AddNewExtractMulti(EmptyObject)
    WorkObject.InsertHybridShape Extract_Cache
    
    
    'Create Spline_Span_Block
    For nSpan = 1 To Num_Span
        For nDivide = 1 To Num_Divide
            For nDu = 1 To 2
                For nIO = 1 To 2
                    
                    If nDu = 1 Then
                        Orientation = Orientation_FaceVector(1)
                    ElseIf nDu = 2 Then
                        Orientation = Orientation_FaceVector(2)
                    End If
                    
                    If nDivide <= 3 And nIO = 1 Then
                        Set Spline_SectionOffset_Point_Cache(nSpan, nDu, nDivide, nIO) = DPH.AddNewPointOnCurveFromPercent(Line_NormalVector(nSpan, nDu, nDivide), 1.05, Not Orientation)
                    Else
                        Set Spline_SectionOffset_Point_Cache(nSpan, nDu, nDivide, nIO) = Spline_SectionOffset_Point(nSpan, nDu, nDivide, nIO)
                    End If
                    
                Next nIO
            Next nDu
        Next nDivide
    Next nSpan
    
    
    For nBlock = 1 To Num_Section - 1
        For nDivide = 1 To Num_Divide
            For nDu = 1 To 2
                For nIO = 1 To 2
    
                    Set Spline_Span_Block(nDivide, nDu, nIO, nBlock * 2) = DPH.AddNewLinePtPt(Spline_SectionOffset_Point_Cache(nBlock * 3 - 1, nDu, nDivide, nIO), _
                                                                                              Spline_SectionOffset_Point_Cache(nBlock * 3, nDu, nDivide, nIO))
                    
                Next nIO
            Next nDu
        Next nDivide
    Next nBlock
    
    
    For nBlock = 1 To Num_Section
        For nDivide = 1 To Num_Divide
            For nDu = 1 To 2
                For nIO = 1 To 2
                    
                    If nBlock = 1 Then
                        
                        Set Spline_ForTangency_Inner = Direction_Y
                        Set Spline_ForTangency_Outer = Spline_Span_Block(nDivide, nDu, nIO, nBlock * 2)
                        
                        
                        Set Spline_Span_Block(nDivide, nDu, nIO, nBlock * 2 - 1) = DPH.AddNewSpline
                        
                        If nDivide = 1 And nIO = 1 Then
                            Spline_Span_Block(nDivide, nDu, nIO, nBlock * 2 - 1).AddPointWithConstraintExplicit Spline_SectionOffset_Point_Cache((nBlock - 1) * 3 + 1, nDu, nDivide, nIO), Nothing, -1#, 1, Nothing, 0#
                        Else
                            Spline_Span_Block(nDivide, nDu, nIO, nBlock * 2 - 1).AddPointWithConstraintFromCurve Spline_SectionOffset_Point_Cache((nBlock - 1) * 3 + 1, nDu, nDivide, nIO), Spline_ForTangency_Inner, 0.5, 1, 1
                        End If
                                              
                        Spline_Span_Block(nDivide, nDu, nIO, nBlock * 2 - 1).AddPointWithConstraintFromCurve Spline_SectionOffset_Point_Cache((nBlock - 1) * 3 + 2, nDu, nDivide, nIO), Spline_ForTangency_Outer, 0.5, 1, 1
                    
                        
                    ElseIf nBlock = Num_Section Then
                    
                        Set Spline_ForTangency_Inner = Spline_Span_Block(nDivide, nDu, nIO, (nBlock - 1) * 2)
                        Set Spline_ForTangency_Outer = DPH.AddNewLinePtPt(Spline_SectionOffset_Point_Cache(Num_Span - 1, nDu, nDivide, nIO), Spline_SectionOffset_Point_Cache(Num_Span, nDu, nDivide, nIO))
                        
                        
                        Set Spline_Span_Block(nDivide, nDu, nIO, nBlock * 2 - 1) = DPH.AddNewSpline
                    
                        Spline_Span_Block(nDivide, nDu, nIO, nBlock * 2 - 1).AddPointWithConstraintFromCurve Spline_SectionOffset_Point_Cache((nBlock - 1) * 3, nDu, nDivide, nIO), Spline_ForTangency_Inner, 1, 1, 1
                                                
                        Spline_Span_Block(nDivide, nDu, nIO, nBlock * 2 - 1).AddPointWithConstraintFromCurve Spline_SectionOffset_Point_Cache((nBlock - 1) * 3 + 1, nDu, nDivide, nIO), Spline_ForTangency_Outer, 1, 1, 1
                        
                    Else
                    
                        Set Spline_ForTangency_Inner = Spline_Span_Block(nDivide, nDu, nIO, (nBlock - 1) * 2)
                        
                        Set Spline_ForTangency_Mid = DPH.AddNewLinePtPt(Spline_SectionOffset_Point_Cache((nBlock - 1) * 3, nDu, nDivide, nIO), Spline_SectionOffset_Point_Cache((nBlock - 1) * 3 + 2, nDu, nDivide, nIO))
                        
                        Set Spline_ForTangency_Outer = Spline_Span_Block(nDivide, nDu, nIO, nBlock * 2)
   
                        
                        Set Spline_Span_Block(nDivide, nDu, nIO, nBlock * 2 - 1) = DPH.AddNewSpline
                        
                        If nDivide = Num_Divide Then
                        
                            Spline_Span_Block(nDivide, nDu, nIO, nBlock * 2 - 1).AddPointWithConstraintFromCurve Spline_SectionOffset_Point_Cache((nBlock - 1) * 3, nDu, nDivide, nIO), Spline_ForTangency_Inner, 1.7, 1, 1
                            
                            Spline_Span_Block(nDivide, nDu, nIO, nBlock * 2 - 1).AddPointWithConstraintExplicit Spline_SectionOffset_Point_Cache((nBlock - 1) * 3 + 1, nDu, nDivide, nIO), Nothing, -1#, 1, Nothing, 0#
                            
                            Spline_Span_Block(nDivide, nDu, nIO, nBlock * 2 - 1).AddPointWithConstraintFromCurve Spline_SectionOffset_Point_Cache((nBlock - 1) * 3 + 2, nDu, nDivide, nIO), Spline_ForTangency_Outer, 1.7, 1, 1
                        
                        Else
                            
                            Spline_Span_Block(nDivide, nDu, nIO, nBlock * 2 - 1).AddPointWithConstraintFromCurve Spline_SectionOffset_Point_Cache((nBlock - 1) * 3, nDu, nDivide, nIO), Spline_ForTangency_Inner, 0.7, 1, 1
                            
                            Spline_Span_Block(nDivide, nDu, nIO, nBlock * 2 - 1).AddPointWithConstraintFromCurve Spline_SectionOffset_Point_Cache((nBlock - 1) * 3 + 1, nDu, nDivide, nIO), Spline_ForTangency_Mid, 0.7, 1, 1
                            
                            Spline_Span_Block(nDivide, nDu, nIO, nBlock * 2 - 1).AddPointWithConstraintFromCurve Spline_SectionOffset_Point_Cache((nBlock - 1) * 3 + 2, nDu, nDivide, nIO), Spline_ForTangency_Outer, 0.7, 1, 1
                        
                        End If

                    End If

                Next nIO
            Next nDu
        Next nDivide
    Next nBlock
    

    'Combine
    For nDu = 1 To 2
        For nDivide = 1 To Num_Divide
            For nIO = 1 To 2
            
                Set Spline_Span(nDu, nDivide, nIO) = DPH.AddNewJoin(Spline_Span_Block(nDivide, nDu, nIO, 1), Spline_Span_Block(nDivide, nDu, nIO, 2))
                                
                For i = 3 To Num_Section * 2 - 1
                    Spline_Span(nDu, nDivide, nIO).AddElement Spline_Span_Block(nDivide, nDu, nIO, i)
                Next i
                
                'WorkObject.InsertHybridShape Spline_Span(nDu, nDivide, nIO)

            Next nIO
        Next nDivide
    Next nDu
    
    
    'Change Spline_Span_Fillet_UpLow
    For nDu = 1 To 2
        
        If nDu = 1 Then
            If Orientation_FaceVector(3) = False Then
                Orientation = 1
            Else
                Orientation = -1
            End If
        Else
            If Orientation_FaceVector(3) = False Then
                Orientation = -1
            Else
                Orientation = 1
            End If
        End If
        
        
        Set Point_1 = Spline_SectionOffset_Point(1, nDu, 10, 1)
        Set Point_2 = Spline_SectionOffset_Point(Num_Span, nDu, 10, 1)
        
        Set Spline_Span_Fillet_UpLow = DPH.AddNewBoundaryOfSurface(Entity_SmoothAndJoint.Surface_Joint_Fillet)
        Spline_Span_Fillet_UpLow.From = Point_1
        Spline_Span_Fillet_UpLow.FromOrientation = Orientation
        Spline_Span_Fillet_UpLow.To = Point_2
        
        Set Spline_Span(nDu, Num_Divide - 1, 1) = Spline_Span_Fillet_UpLow
        
        'WorkObject.InsertHybridShape Spline_Span(nDU, Num_Divide - 1, 1)
        
    Next nDu
    
    
    'Change Spline_Span_Fillet_Mid
    For nSpan = 1 To Num_Span - 1
        
        Set Spline_1 = Spline_SectionProject_Fillet(nSpan)
        Set Spline_2 = Spline_SectionProject_Fillet(nSpan + 1)

        Set Point_1 = DPH.AddNewPointOnCurveFromPercent(Spline_1, 0.5, False)
        Set Point_2 = DPH.AddNewPointOnCurveFromPercent(Spline_2, 0.5, False)
        
        Set Line_1 = DPH.AddNewLinePtPt(Point_1, Point_2)
        
        
        Span_Half = Data_SectionPoint(Num_Section * Num_PointPerSpline, 2) - Data_SectionPoint(Num_PointPerSpline, 2)
        
        Length_Line_Guide = GetDistance(Point_1, Point_2, DocumentObject, Extract_Cache)
        
        Num_PointPerBlock = Round(Length_Line_Guide / (Span_Half / 100)) + 1
        
        If (nSpan + 1) Mod 3 <> 0 Then
            Num_PointPerBlock = Num_PointPerBlock * 2
        End If
        
 
        Set Spline_Span_MidFillet_Block(nSpan) = DPH.AddNewSpline
        
        For nPoint = 1 To Num_PointPerBlock + 1
            
            If (nSpan + 1) Mod 3 <> 0 Then
            
                If nSpan Mod 3 <> 0 Then
            
                    x0 = (nPoint - 1) / Num_PointPerBlock
                    
                    K = 1 - Cos(x0 * Pi / 2)
                
                Else
                    
                    x0 = (nPoint - 1) / Num_PointPerBlock
                    
                    K = -Cos((x0 + 1) * Pi / 2)
                
                End If
            
            Else
            
                K = (nPoint - 1) / Num_PointPerBlock
            
            End If
            
                
            Set Point_1 = DPH.AddNewPointOnCurveFromPercent(Line_1, K, False)
            
            If nPoint <> 1 And nPoint <> Num_PointPerBlock + 1 Then
            
                Set Flat_1 = DPH.AddNewPlaneNormal(Line_1, Point_1)
    
                Set Spline_1 = DPH.AddNewIntersection(Flat_1, Entity_SmoothAndJoint.Surface_Joint_Fillet)
                
                Set Point_1 = DPH.AddNewPointOnCurveFromPercent(Spline_1, 0.5, False)
            
            End If
            
            Spline_Span_MidFillet_Block(nSpan).AddPointWithConstraintExplicit Point_1, Nothing, -1#, 1, Nothing, 0#
        
        Next nPoint
        
    Next nSpan
    
    
    'Combine
    For nDu = 1 To 2

        Set Spline_Span_MidFillet = DPH.AddNewJoin(Spline_Span_MidFillet_Block(1), Spline_Span_MidFillet_Block(2))

        For nSpan = 3 To Num_Span - 1
            Spline_Span_MidFillet.AddElement Spline_Span_MidFillet_Block(nSpan)
        Next nSpan

        Set Spline_Span(nDu, Num_Divide, 1) = Spline_Span_MidFillet
        
        
        'WorkObject.InsertHybridShape Spline_Span(nDu, Num_Divide, 1)

    Next nDu
    
    
    'Project
    Set Extract_Surface_Joint_UpLow = DPH.AddNewExtractMulti(Entity_SmoothAndJoint.Surface_Joint_UpLow_Low)
    
    Extract_Surface_Joint_UpLow.AddConstraintTolerant Entity_SmoothAndJoint.Surface_Joint_UpLow_Low, 3, False, False, 0.1, 0.5, 0.98, 1
    Extract_Surface_Joint_UpLow.SetElement 1, Entity_SmoothAndJoint.Surface_Joint_UpLow_Low
    
    Extract_Surface_Joint_UpLow.AddConstraintTolerant Entity_SmoothAndJoint.Surface_Joint_UpLow_Up, 3, False, False, 0.1, 0.5, 0.98, 1
    Extract_Surface_Joint_UpLow.SetElement 1, Entity_SmoothAndJoint.Surface_Joint_UpLow_Up
    
    
    For nDu = 1 To 2
        For nDivide = 1 To Num_Divide - 2
            
            If nDivide <= 3 Or nDivide >= 8 Then
            
                If nDu = 1 Then
                    Orientation = Orientation_FaceVector(1)
                ElseIf nDu = 2 Then
                    Orientation = Orientation_FaceVector(2)
                End If
            
                For nSpan = 1 To Num_Span
                    
                    Set Point_1 = Spline_SectionOffset_Point_Cache(nSpan, nDu, nDivide, 1)
                    
                    Set Direction_Extrude = DPH.AddNewDirection(Line_NormalVector(nSpan, nDu, nDivide))
                    
                    If nDivide = 1 Then
                    
                        Length_Extrude = 0.004 * Length_Chord_BlockSection(nSpan)
                        
                    ElseIf nDivide = 2 Or nDivide = 3 Then
                    
                        Length_Extrude = 0.05 * Length_Chord_BlockSection(nSpan)
                        
                    Else
                        
                        Length_Extrude = 0.1 * Length_Chord_BlockSection(nSpan)
                        
                    End If
                    
                    Set Line_ToIntersect_Block(nSpan) = DPH.AddNewLinePtDir(Point_1, Direction_Extrude, -Length_Extrude, 0, Orientation)
                    
                Next nSpan
                
                
                Set Surface_ToIntersect_Total = DPH.AddNewLoft
                
                For nSpan = 1 To Num_Span
    
                    Surface_ToIntersect_Total.AddSectionToLoft Line_ToIntersect_Block(nSpan), 1, Nothing
    
                Next nSpan
                
                Surface_ToIntersect_Total.AddGuide Spline_Span(nDu, nDivide, 1)
                
                
                Length_Extrapol = (Length_Chord(1) + Length_Chord(Num_Section)) * 0.02 / 2
                
                Set Surface_ToIntersect_Total = DPH.AddNewExtrapolLength(Spline_Span(nDu, nDivide, 1), Surface_ToIntersect_Total, Length_Extrapol)
                Surface_ToIntersect_Total.BorderType = 1
                Surface_ToIntersect_Total.SetAssemble True
                Surface_ToIntersect_Total.SetContinuityType 0, 1
                
                'WorkObject.InsertHybridShape Surface_ToIntersect_Total
                
    
                If nDivide = 1 Then
                    Set Surface_ForIntersect = Extract_Surface_Joint_UpLow
                Else
                    If nDu = 1 Then
                        Set Surface_ForIntersect = Entity_SmoothAndJoint.Surface_Joint_UpLow_Low
                    Else
                        Set Surface_ForIntersect = Entity_SmoothAndJoint.Surface_Joint_UpLow_Up
                    End If
                End If
                    
                Set Spline_Span(nDu, nDivide, 1) = DPH.AddNewIntersection(Surface_ToIntersect_Total, Surface_ForIntersect)
            
            Else
                
                If nDu = 1 Then
                    Set Surface_ForIntersect = Entity_SmoothAndJoint.Surface_Joint_UpLow_Low
                Else
                    Set Surface_ForIntersect = Entity_SmoothAndJoint.Surface_Joint_UpLow_Up
                End If
                    
                Set Spline_Span(nDu, nDivide, 1) = DPH.AddNewProject(Spline_Span(nDu, nDivide, 1), Surface_ForIntersect)
                Spline_Span(nDu, nDivide, 1).Normal = True
            
            End If
            
            'WorkObject.InsertHybridShape Spline_Span(nDu, nDivide, 1)
            
        Next nDivide
    Next nDu
    
    
    Set Surface_1 = DPH.AddNewExtrude(Spline_Span(1, Num_Divide, 1), Diameter_Fillet, Diameter_Fillet, Direction_X)
    
    Set Spline_Span(1, Num_Divide, 1) = DPH.AddNewIntersection(Surface_1, Entity_SmoothAndJoint.Surface_Joint_Fillet)
    
    Set Spline_Span(2, Num_Divide, 1) = Spline_Span(1, Num_Divide, 1)
    
    
    'Hide
    DocumentObject.Selection.Add Extract_Cache
    DocumentObject.Selection.VisProperties.SetShow 1
    DocumentObject.Selection.Clear
    
    
'-----------------------------------
'Deal Tip
'-----------------------------------

    '-----------------------------------
    'Create Spline_SectionProject_Tip
    '-----------------------------------
    Dim Direction_Project_Tip_y(1 To MaxNum_Array) As Object
    Dim Line_ToProject_Tip_y(1 To MaxNum_Array) As Object
    Dim Spline_SectionProject_Tip_y(1 To MaxNum_Array) As Object
    
    Dim Spline_SectionProject_Tip_x_Point(1 To MaxNum_Array) As Object
    

    'Create Spline_SectionProject_Tip_y
    For nDivide = 2 To Num_Divide - 2
        
        Set Line_1 = DPH.AddNewLineTangency(Spline_Span(1, nDivide, 1), Spline_SectionOffset_Point(Num_Span, 1, nDivide, 1), 0, 0.1 * Length_Chord(Num_Section), False)
        
        Set Direction_Project_Tip_y(nDivide) = DPH.AddNewDirection(Line_1)

    Next nDivide
    
    For nDivide = 2 To Num_Divide - 2
        
        Set Line_ToProject_Tip_y(nDivide) = DPH.AddNewLinePtPt(Spline_SectionOffset_Point(Num_Span, 1, nDivide, 1), Spline_SectionOffset_Point(Num_Span, 2, nDivide, 1))
        
        Set Point_1 = DPH.AddNewPointOnCurveFromPercent(Line_ToProject_Tip_y(nDivide), 0, False)
        Set Point_2 = DPH.AddNewPointOnCurveFromPercent(Line_ToProject_Tip_y(nDivide), 1, False)
        
        Set Line_ToProject_Tip_y(nDivide) = DPH.AddNewExtrapolLength(Point_1, Line_ToProject_Tip_y(nDivide), 0.1 * Length_Chord(Num_Section))
        Line_ToProject_Tip_y(nDivide).BorderType = 1
        Line_ToProject_Tip_y(nDivide).SetAssemble True
        Line_ToProject_Tip_y(nDivide).SetContinuityType 1, 1
                
        Set Line_ToProject_Tip_y(nDivide) = DPH.AddNewExtrapolLength(Point_2, Line_ToProject_Tip_y(nDivide), 0.1 * Length_Chord(Num_Section))
        Line_ToProject_Tip_y(nDivide).BorderType = 1
        Line_ToProject_Tip_y(nDivide).SetAssemble True
        Line_ToProject_Tip_y(nDivide).SetContinuityType 1, 1
        
        'WorkObject.InsertHybridShape Line_ToProject_Tip_y(nDivide)
            
    Next nDivide
          
    For nDivide = 2 To Num_Divide - 1
        
        If nDivide <> Num_Divide - 1 Then
         
            Set Spline_SectionProject_Tip_y(nDivide) = DPH.AddNewProject(Line_ToProject_Tip_y(nDivide), Entity_SmoothAndJoint.Surface_Joint_Tip)
            Spline_SectionProject_Tip_y(nDivide).Normal = False
            Spline_SectionProject_Tip_y(nDivide).Direction = Direction_Project_Tip_y(nDivide)
  
        Else
        
            Set Spline_SectionProject_Tip_y(nDivide) = DPH.AddNewExtractMulti(Entity_SmoothAndJoint.Spline_Tip_y(Num_Divide))
            Spline_SectionProject_Tip_y(nDivide).AddConstraintTolerant Entity_SmoothAndJoint.Spline_Tip_y(Num_Divide), 3, False, False, 0.1, 0.5, 0.98, 1
            Spline_SectionProject_Tip_y(nDivide).SetElement 1, Entity_SmoothAndJoint.Spline_Tip_y(Num_Divide)
            
        End If
        
        'WorkObject.InsertHybridShape Spline_SectionProject_Tip_y(nDivide)
        
    Next nDivide


    'Create Spline_SectionProject_Tip_x
    Set Spline_SectionProject_Tip_x = DPH.AddNewSpline

    For nDivide = 2 To Num_Divide - 1
        
        If nDivide <> Num_Divide - 2 Then
        
            Set Spline_SectionProject_Tip_x_Point(nDivide) = DPH.AddNewPointOnCurveFromPercent(Spline_SectionProject_Tip_y(nDivide), 0.5, False)
    
            Spline_SectionProject_Tip_x.AddPointWithConstraintExplicit Spline_SectionProject_Tip_x_Point(nDivide), Nothing, -1#, 1, Nothing, 0#
        
        End If
        
    Next nDivide

    'WorkObject.InsertHybridShape Spline_SectionProject_Tip_x
    
    
    '-----------------------------------
    'Deal Tip Inner
    '-----------------------------------
    Dim Spline_LeadOrTrail_Total_Inner(1 To 2) As Object
    Dim Spline_LeadOrTrail_Inner(1 To 2, 1 To 2) As Object
    
    
    Set Extract_Cache = DPH.AddNewExtractMulti(EmptyObject)
    WorkObject.InsertHybridShape Extract_Cache
    
    
    For nDeal = 1 To 2
        
        'Create Direction_Project_Tip
        If nDeal = 1 Then
            Angle_Rotate = -((360 - Angle_Tip_Lead) / 2 - (180 - Angle_Tip_Lead))
            Index = 2
        Else
            Angle_Rotate = (360 - Angle_Tip_Trail) / 2 - (180 - Angle_Tip_Trail)
            Index = Num_Divide - 1
        End If
        
        
        Set Line_Axis = DPH.AddNewLinePtPt(Spline_SectionOffset_Point(Num_Span, 1, Index, 1), Spline_SectionOffset_Point(Num_Span, 2, Index, 1))
            
        Set Point_1 = DPH.AddNewPointOnCurveFromPercent(Line_Axis, 0, False)
        Set Point_2 = DPH.AddNewPointOnCurveFromPercent(Line_Axis, 1, False)
        
        Set Line_Axis = DPH.AddNewExtrapolLength(Point_1, Line_Axis, 0.1 * Length_Chord(Num_Section))
        Line_Axis.BorderType = 1
        Line_Axis.SetAssemble True
        Line_Axis.SetContinuityType 1, 1
                
        Set Line_Axis = DPH.AddNewExtrapolLength(Point_2, Line_Axis, 0.1 * Length_Chord(Num_Section))
        Line_Axis.BorderType = 1
        Line_Axis.SetAssemble True
        Line_Axis.SetContinuityType 1, 1
        
        
        Set Line_x = DPH.AddNewLinePtDir(Spline_SectionOffset_Point(Num_Span, 2, Index, 1), Direction_X, 0, 0.1 * Length_Chord(Num_Section) * (-1) ^ nDeal, False)
    
        Set Line_Rotate = DPH.AddNewEmptyRotate()
        Line_Rotate.ElemToRotate = Line_x
        Line_Rotate.Axis = Line_Axis
        Line_Rotate.AngleValue = Angle_Rotate
        
        Set Direction_Project_Tip = DPH.AddNewDirection(Line_Rotate)
        
        
        'Create Spline_LeadOrTrail
        Set Spline_LeadOrTrail_Total_Inner(nDeal) = DPH.AddNewProject(Line_Axis, Entity_SmoothAndJoint.Surface_Joint_Tip)
        Spline_LeadOrTrail_Total_Inner(nDeal).Normal = False
        Spline_LeadOrTrail_Total_Inner(nDeal).Direction = Direction_Project_Tip
         
         
        'Create And Combine
        If nDeal = 1 Then
            Index = 1
        Else
            Index = Num_Divide
        End If
        
        Set Point_1 = Spline_SectionOffset_Point(Num_Span - 1, 1, Index, 1)
        Set Point_2 = Spline_SectionOffset_Point(Num_Span, 1, Index, 1)
        Set Point_3 = DPH.AddNewPointOnCurveFromPercent(Spline_LeadOrTrail_Total_Inner(nDeal), 0.5, False)
        Set Point_4 = DPH.AddNewPointOnCurveFromPercent(Spline_SectionProject_Tip_y(Index + (-1) ^ (nDeal + 1)), 0.5, False)
        
        Set Line_1 = DPH.AddNewLinePtPt(Point_1, Point_2)
        
        
        Set Spline_1 = DPH.AddNewSpline
        
        Spline_1.AddPointWithConstraintFromCurve Point_2, Line_1, 1, 1, 1
        
        If nDeal <> 1 Then
            Spline_1.AddPointWithConstraintExplicit Point_3, Nothing, -1#, 1, Nothing, 0#
        End If
        
        Spline_1.AddPointWithConstraintFromCurve Point_4, Spline_SectionProject_Tip_x, 1, (-1) ^ (nDeal + 1), 1
        
        'Set Spline_SectionProject_Tip_x = DPH.AddNewJoin(Spline_SectionProject_Tip_x, Spline_1)

        
        'Split Spline_LeadOrTrail
        If nDeal = 1 Then
        
            Set Spline_SectionProject_Tip_x_ForIntersect = DPH.AddNewProject(Spline_1, Entity_SmoothAndJoint.Surface_Joint_Tip_Front)
            
            Spline_SectionProject_Tip_x_ForIntersect.Normal = True
            
        Else
        
            Set Line_1 = DPH.AddNewLineAngle(Direction_X, PLANE_XY, Point_3, False, 0, 0.1 * MAC_Length, Angle_Tip_Trail / 2, True)

            Set Direction_Extrude = DPH.AddNewDirection(Line_1)
            
            Set Surface_ToIntersect_Trail = DPH.AddNewExtrude(Spline_1, LayerHeight_BlockSection(Num_Span), LayerHeight_BlockSection(Num_Span), Direction_Extrude)
            
            Set Spline_SectionProject_Tip_x_ForIntersect = DPH.AddNewIntersection(Surface_ToIntersect_Trail, Entity_SmoothAndJoint.Surface_Joint_Tip_Trail)
        
        End If
        
        Set Point_Center = DPH.AddNewIntersection(Spline_SectionProject_Tip_x_ForIntersect, Spline_LeadOrTrail_Total_Inner(nDeal))


        Orientation = Orientation_ForSplit_ByZ(Spline_LeadOrTrail_Total_Inner(nDeal), Point_Center, DocumentObject, Extract_Cache)

        Set Spline_LeadOrTrail_Inner(nDeal, 1) = DPH.AddNewHybridSplit(Spline_LeadOrTrail_Total_Inner(nDeal), Point_Center, Orientation)
        Set Spline_LeadOrTrail_Inner(nDeal, 2) = DPH.AddNewHybridSplit(Spline_LeadOrTrail_Total_Inner(nDeal), Point_Center, -Orientation)
        

        'Change Spline_SectionProject
        For nDu = 1 To 2
            
            Orientation = Orientation_ForSplit_ByX(Spline_SectionProject(Num_Span, nDu), Spline_LeadOrTrail_Inner(nDeal, nDu), DocumentObject, Extract_Cache)

            Set Spline_Mid = DPH.AddNewHybridSplit(Spline_SectionProject(Num_Span, nDu), Spline_LeadOrTrail_Inner(nDeal, nDu), Orientation * (-1) ^ nDeal)

            Set Spline_SectionProject(Num_Span, nDu) = DPH.AddNewJoin(Spline_LeadOrTrail_Inner(nDeal, nDu), Spline_Mid)
            
        Next nDu
        
        
        'Change Spline_SectionProject_Tip_x_Point
        If nDeal = 1 Then
            Index = 2
        Else
            Index = Num_Divide - 1
        End If
        
        Set Spline_SectionProject_Tip_x_Point(Index) = Point_Center
        
        
        'Project Spline_SectionProject_Tip_x
        If nDeal = 1 Then
            
            Set Point_1 = DPH.AddNewPointOnCurveFromPercent(Spline_SectionProject_Tip_x, 0, False)
            Set Point_2 = DPH.AddNewPointOnCurveFromPercent(Spline_SectionProject_Tip_x, 1, False)
            
            Set Line_Axis = DPH.AddNewLinePtPt(Point_1, Point_2)
            
            Set Spline_Rotate = DPH.AddNewEmptyRotate()
            Spline_Rotate.ElemToRotate = Spline_SectionProject_Tip_x
            Spline_Rotate.Axis = Line_Axis
            Spline_Rotate.AngleValue = 2
            
            Set Spline_SectionProject_Tip_x = DPH.AddNewJoin(Spline_Rotate, Spline_SectionProject_Tip_x_ForIntersect)
            
            
            Orientation = Orientation_ForPercent_ByX(Spline_SectionProject_Tip_x, DocumentObject, Extract_Cache)
            
            Set Point_1 = DPH.AddNewPointOnCurveFromPercent(Spline_SectionProject_Tip_x, 0, Orientation)
            
            Set Spline_1 = DPH.AddNewExtrapolLength(Point_1, Spline_SectionProject_Tip_x, 0.05 * Length_Chord(Num_Section))
            Spline_1.BorderType = 1
            Spline_1.SetAssemble True
            Spline_1.SetContinuityType 1, 0
            
            
            Set Direction_1 = DPH.AddNewDirectionByCoord(-1, 1.732, 0)
            
            Set Surface_ForIntersect = DPH.AddNewExtrude(Spline_1, 0.05 * Length_Chord(Num_Section), 0.05 * Length_Chord(Num_Section), Direction_1)
                    
            Set Spline_SectionProject_Tip_x = DPH.AddNewIntersection(Surface_ForIntersect, Entity_SmoothAndJoint.Surface_Joint_Tip_Front)
            
        Else
        
            Set Spline_SectionProject_Tip_x_Front = DPH.AddNewProject(Spline_SectionProject_Tip_x, Entity_SmoothAndJoint.Surface_Joint_Tip_Front)
            Spline_SectionProject_Tip_x_Front.Normal = True
            
            Set Spline_SectionProject_Tip_x_Trail = DPH.AddNewIntersection(Surface_ToIntersect_Trail, Entity_SmoothAndJoint.Surface_Joint_Tip_Trail)


            Set Spline_SectionProject_Tip_x = DPH.AddNewJoin(Spline_SectionProject_Tip_x_Front, Spline_SectionProject_Tip_x_Trail)
            
        End If
        

        'Change Spline_Span And Spline_SectionProject_Tip_x
        Orientation = Orientation_ForSplit_ByX(Spline_SectionProject_Tip_x, Point_Center, DocumentObject, Extract_Cache)

        Set Spline_1 = DPH.AddNewHybridSplit(Spline_SectionProject_Tip_x, Point_Center, Orientation * (-1) ^ (nDeal + 1))
        
        
        If nDeal = 1 Then
            Index = 1
        Else
            Index = Num_Divide
        End If
        
        Set Spline_Span(1, Index, 1) = DPH.AddNewJoin(Spline_Span(1, Index, 1), Spline_1)
        
        If nDeal = 1 Then
            Deviation = Deviation_Bridge
        ElseIf nDeal = 2 Then
            Deviation = Deviation_Bridge + 0.01
        End If
        
        Spline_Span(1, Index, 1).SetDeviation Deviation
        
        Set Spline_Span(2, Index, 1) = Spline_Span(1, Index, 1)


        Set Spline_SectionProject_Tip_x = DPH.AddNewHybridSplit(Spline_SectionProject_Tip_x, Point_Center, -Orientation * (-1) ^ (nDeal + 1))
    
    Next nDeal
 

    'Hide
    DocumentObject.Selection.Add Extract_Cache
    DocumentObject.Selection.VisProperties.SetShow 1
    DocumentObject.Selection.Clear
    
    
    '-----------------------------------
    'Create Line_NormalVector_Tip
    '-----------------------------------
    Dim Line_NormalVector_Tip(1 To MaxNum_Array) As Object
    
    
    Set Extract_Cache = DPH.AddNewExtractMulti(EmptyObject)
    WorkObject.InsertHybridShape Extract_Cache
    
    
    'Solve Orientation_FaceVector
    Set Surface_1 = Entity_SmoothAndJoint.Surface_Joint_Tip
    Set Point_1 = DPH.AddNewIntersection(Spline_SectionProject_Tip_x, Spline_SectionProject_Tip_y(4))
    
    Set Line_1 = DPH.AddNewLineNormal(Surface_1, Point_1, 0, LayerHeight_BlockSection(Num_Span), False)
    Set Line_2 = DPH.AddNewLineNormal(Surface_1, Point_1, 0, LayerHeight_BlockSection(Num_Span), True)
    
    Set Point_1 = DPH.AddNewPointOnCurveFromPercent(Line_1, 0.5, False)
    Set Point_2 = DPH.AddNewPointOnCurveFromPercent(Line_2, 0.5, False)
    
    Extract_Cache.AddConstraintTolerant Point_1, 3, False, False, 0.1, 0.5, 0.98, 1
    Extract_Cache.SetElement 1, Point_1
                
    Extract_Cache.AddConstraintTolerant Point_2, 3, False, False, 0.1, 0.5, 0.98, 1
    Extract_Cache.SetElement 1, Point_2
    DocumentObject.Part.Update
    
    Point_1.GetCoordinates XYZ_Cache
    Y1 = XYZ_Cache(1)

    Point_2.GetCoordinates XYZ_Cache
    Y2 = XYZ_Cache(1)
    
    If Y1 > Y2 Then
        Orientation_FaceVector(4) = False
    Else
        Orientation_FaceVector(4) = True
    End If
    
        
    'Create Line_NormalVector_Tip
    For nDivide = 2 To Num_Divide - 1
    
        Set Point_1 = DPH.AddNewIntersection(Spline_SectionProject_Tip_x, Spline_SectionProject_Tip_y(nDivide))
        
        Set Line_NormalVector_Tip(nDivide) = DPH.AddNewLineNormal(Entity_SmoothAndJoint.Surface_Joint_Tip, Point_1, 0, LayerHeight_BlockSection(Num_Span), Orientation_FaceVector(4))
        
        'WorkObject.InsertHybridShape Line_NormalVector_Tip(nDivide)
        
    Next nDivide
        
    
    'Hide
    DocumentObject.Selection.Add Extract_Cache
    DocumentObject.Selection.VisProperties.SetShow 1
    DocumentObject.Selection.Clear
    
    
    '-----------------------------------
    'Create Spline_SectionOffset_Tip
    '-----------------------------------
    Dim Spline_SectionOffset_Tip_y(1 To MaxNum_Array) As Object
    
    
    'Create Spline_SectionOffset_Tip_y
    For nDivide = 2 To Num_Divide - 1
        
        Set Spline_SectionOffset_Tip_y(nDivide) = DPH.AddNewSpline

        Spline_SectionOffset_Tip_y(nDivide).AddPointWithConstraintFromCurve Spline_SectionOffset_Point(Num_Span, 1, nDivide, 2), Spline_Span(1, nDivide, 2), 1, 1, 1
        
        Set Point_1 = DPH.AddNewPointOnCurveFromPercent(Line_NormalVector_Tip(nDivide), 1, Orientation_FaceVector(4))
        Spline_SectionOffset_Tip_y(nDivide).AddPointWithConstraintExplicit Point_1, Nothing, -1#, 1, Nothing, 0#
        
        Spline_SectionOffset_Tip_y(nDivide).AddPointWithConstraintFromCurve Spline_SectionOffset_Point(Num_Span, 2, nDivide, 2), Spline_Span(2, nDivide, 2), 1, -1, 1
        
        'WorkObject.InsertHybridShape Spline_SectionOffset_Tip_y(nDivide)

    Next nDivide
    
    
    'Change Line_NormalVector_Tip
    For nDivide = 2 To Num_Divide - 1
    
        Set Point_1 = DPH.AddNewIntersection(Spline_SectionProject_Tip_x, Spline_SectionProject_Tip_y(nDivide))
        
        Set Point_2 = DPH.AddNewPointOnCurveFromPercent(Spline_SectionOffset_Tip_y(nDivide), 0.5, False)
        
        Set Line_NormalVector_Tip(nDivide) = DPH.AddNewLinePtPt(Point_1, Point_2)
        
        'WorkObject.InsertHybridShape Line_NormalVector_Tip(nDivide)
        
    Next nDivide
    
    
    'Create Spline_SectionOffset_Tip_x
    Set Spline_SectionOffset_Tip_x_Mid = DPH.AddNewSpline

    For nDivide = 2 To Num_Divide - 1
    
        If nDivide <> Num_Divide - 2 Then

            Set Point_1 = DPH.AddNewPointOnCurveFromPercent(Line_NormalVector_Tip(nDivide), 1, False)
    
            Spline_SectionOffset_Tip_x_Mid.AddPointWithConstraintExplicit Point_1, Nothing, -1#, 1, Nothing, 0#
        
        End If
        
    Next nDivide
    
    'WorkObject.InsertHybridShape Spline_SectionOffset_Tip_x_Mid


    Set Point_1 = Spline_SectionOffset_Point(Num_Span - 1, 1, 1, 2)
    Set Point_2 = Spline_SectionOffset_Point(Num_Span, 1, 1, 2)
    Set Point_3 = DPH.AddNewPointOnCurveFromPercent(Line_NormalVector_Tip(2), 1, False)
    
    Set Line_1 = DPH.AddNewLinePtPt(Point_1, Point_2)
    
    Set Spline_SectionOffset_Tip_x_Lead = DPH.AddNewSpline
    Spline_SectionOffset_Tip_x_Lead.AddPointWithConstraintFromCurve Point_2, Line_1, 1, 1, 1
    Spline_SectionOffset_Tip_x_Lead.AddPointWithConstraintFromCurve Point_3, Spline_SectionOffset_Tip_x_Mid, 1, 1, 1
    
    'WorkObject.InsertHybridShape Spline_SectionOffset_Tip_x_Lead


    Set Point_1 = Spline_SectionOffset_Point(Num_Span - 1, 1, Num_Divide, 2)
    Set Point_2 = Spline_SectionOffset_Point(Num_Span, 1, Num_Divide, 2)
    Set Point_3 = DPH.AddNewPointOnCurveFromPercent(Line_NormalVector_Tip(Num_Divide - 1), 1, False)
    
    Set Line_1 = DPH.AddNewLinePtPt(Point_1, Point_2)
    
    Set Spline_SectionOffset_Tip_x_Trail = DPH.AddNewSpline
    Spline_SectionOffset_Tip_x_Trail.AddPointWithConstraintFromCurve Point_2, Line_1, 1, 1, 1
    Spline_SectionOffset_Tip_x_Trail.AddPointWithConstraintFromCurve Point_3, Spline_SectionOffset_Tip_x_Mid, 1, -1, 1
    
    'WorkObject.InsertHybridShape Spline_SectionOffset_Tip_x_Trail

        
    Set Spline_SectionOffset_Tip_x = DPH.AddNewJoin(Spline_SectionOffset_Tip_x_Lead, Spline_SectionOffset_Tip_x_Mid)
    Spline_SectionOffset_Tip_x.AddElement Spline_SectionOffset_Tip_x_Trail
    
    'WorkObject.InsertHybridShape Spline_SectionOffset_Tip_x
    
    
    'Change Line_NormalVector_Tip
    Set Point_1 = DPH.AddNewPointOnCurveFromPercent(Line_NormalVector_Tip(Num_Divide - 2), 0, Orientation_FaceVector(4))
    
    Set Point_2 = DPH.AddNewPointOnCurveFromPercent(Spline_SectionOffset_Tip_x_Trail, 0.85, False)

    Set Line_NormalVector_Tip(Num_Divide - 2) = DPH.AddNewLinePtPt(Point_1, Point_2)
    
    
    'Change Spline_SectionOffset_Tip_y
    Set Spline_SectionOffset_Tip_y(Num_Divide - 2) = DPH.AddNewSpline

    Spline_SectionOffset_Tip_y(Num_Divide - 2).AddPointWithConstraintFromCurve Spline_SectionOffset_Point(Num_Span, 1, Num_Divide - 2, 2), Spline_Span(1, Num_Divide - 2, 2), 1, 1, 1
    
    Set Point_1 = DPH.AddNewPointOnCurveFromPercent(Line_NormalVector_Tip(Num_Divide - 2), 1, Orientation_FaceVector(4))
    Spline_SectionOffset_Tip_y(Num_Divide - 2).AddPointWithConstraintExplicit Point_1, Nothing, -1#, 1, Nothing, 0#
    
    Spline_SectionOffset_Tip_y(Num_Divide - 2).AddPointWithConstraintFromCurve Spline_SectionOffset_Point(Num_Span, 2, Num_Divide - 2, 2), Spline_Span(2, Num_Divide - 2, 2), 1, -1, 1
    

    '-----------------------------------
    'Deal Tip Outer
    '-----------------------------------
    Dim Spline_LeadOrTrail_Total_Outer(1 To 2) As Object
    Dim Spline_LeadOrTrail_Outer(1 To 2, 1 To 2) As Object
    
    Dim Spline_SectionOffset_Tip_Point(1 To MaxNum_Array, 1 To 2) As Object
    
    
    Set Extract_Cache = DPH.AddNewExtractMulti(EmptyObject)
    WorkObject.InsertHybridShape Extract_Cache
    
    
    For nDeal = 1 To 2
    
        'Create Spline_LeadOrTrail
        If nDeal = 1 Then
            Index = 2
        Else
            Index = Num_Divide - 1
        End If
        
        
        Set Point_1 = Spline_SectionOffset_Point(Num_Span, 1, Index, 2)
        
        If nDeal = 1 Then
            
            Set Point_2 = DPH.AddNewPointOnCurveFromPercent(Spline_SectionOffset_Tip_x_Lead, 0.5, False)

        Else
            
            Set Point_2 = DPH.AddNewPointOnCurveFromPercent(Spline_SectionOffset_Tip_x_Trail, 0.5, False)
       
        End If
        
        Set Point_3 = Spline_SectionOffset_Point(Num_Span, 2, Index, 2)
        
        
        Set Spline_LeadOrTrail_Total_Outer(nDeal) = DPH.AddNewSpline
        
        Spline_LeadOrTrail_Total_Outer(nDeal).AddPointWithConstraintExplicit Point_1, Nothing, -1#, -1, Nothing, 0#
        Spline_LeadOrTrail_Total_Outer(nDeal).AddPointWithConstraintExplicit Point_2, Nothing, -1#, -1, Nothing, 0#
        Spline_LeadOrTrail_Total_Outer(nDeal).AddPointWithConstraintExplicit Point_3, Nothing, -1#, -1, Nothing, 0#
        

        'Split Spline_LeadOrTrail
        Set Point_Center = DPH.AddNewIntersection(Spline_SectionOffset_Tip_x, Spline_LeadOrTrail_Total_Outer(nDeal))
        
        Set Spline_LeadOrTrail_Outer(nDeal, 1) = DPH.AddNewHybridSplit(Spline_LeadOrTrail_Total_Outer(nDeal), Point_Center, 1)
        Set Spline_LeadOrTrail_Outer(nDeal, 2) = DPH.AddNewHybridSplit(Spline_LeadOrTrail_Total_Outer(nDeal), Point_Center, -1)
        
        
        'Change Spline_SectionOffset
        For nDu = 1 To 2

            Orientation = Orientation_ForSplit_ByX(Spline_SectionOffset(Num_Span, nDu), Spline_LeadOrTrail_Outer(nDeal, nDu), DocumentObject, Extract_Cache)
            
            Set Spline_1 = DPH.AddNewHybridSplit(Spline_SectionOffset(Num_Span, nDu), Spline_LeadOrTrail_Outer(nDeal, nDu), Orientation * (-1) ^ nDeal)

            Set Spline_SectionOffset(Num_Span, nDu) = DPH.AddNewJoin(Spline_LeadOrTrail_Outer(nDeal, nDu), Spline_1)
            
        Next nDu
        
 
        'Change Line_NormalVector
        If nDeal = 1 Then
            Index = 2
            Set Spline_ToCreatePoint = Spline_SectionOffset_Tip_x_Lead
        Else
            Index = Num_Divide - 1
            Set Spline_ToCreatePoint = Spline_SectionOffset_Tip_x_Trail
        End If
        
        
        Set Point_1 = Spline_SectionProject_Tip_x_Point(Index)
        
        Set Point_2 = DPH.AddNewPointOnCurveFromPercent(Spline_ToCreatePoint, 0.5, False)

        
        Set Line_1 = DPH.AddNewLinePtPt(Point_1, Point_2)
        
        Set Line_NormalVector(Num_Span, 1, Index - (-1) ^ (nDeal + 1)) = Line_1
        Set Line_NormalVector(Num_Span, 2, Index - (-1) ^ (nDeal + 1)) = Line_NormalVector(Num_Span, 1, Index - (-1) ^ (nDeal + 1))
        
        
        If nDeal = 2 Then
                        
            Set Line_NormalSurface = DPH.AddNewLineNormal(Entity_SmoothAndJoint.Surface_Joint_Tip, Point_1, 0, 0.1 * Length_Chord(Num_Section), Orientation_FaceVector(4))
            
            
            Set Line_NormalVector(Num_Span, 1, Num_Divide) = DPH.AddNewSpline

            Line_NormalVector(Num_Span, 1, Num_Divide).AddPointWithConstraintFromCurve Point_1, Line_NormalSurface, 0.2, 1, 1
            Line_NormalVector(Num_Span, 1, Num_Divide).AddPointWithConstraintFromCurve Point_2, Line_1, 0.5, 1, 1
            
            
            Set Line_NormalVector(Num_Span, 2, Num_Divide) = Line_NormalVector(Num_Span, 1, Num_Divide)
            
        End If
        

        'Create Spline_SectionOffset_Tip_Point
        For nTip = 1 To Num_Divide - 4
        
            nDivide = nTip + 2
            
            Set Spline_SectionOffset_Tip_Point(nTip, 1) = DPH.AddNewPointOnCurveFromPercent(Line_NormalVector_Tip(nDivide), 0, Orientation_FaceVector(4))
            Set Spline_SectionOffset_Tip_Point(nTip, 2) = DPH.AddNewPointOnCurveFromPercent(Line_NormalVector_Tip(nDivide), 1, Orientation_FaceVector(4))

        Next nTip
        
        
        'Change Spline_SectionOffset_Point
        If nDeal = 1 Then
            Index = 1
        Else
            Index = Num_Divide
        End If
        
        
        Set Spline_SectionOffset_Point(Num_Span, 1, Index, 1) = DPH.AddNewPointOnCurveFromPercent(Line_NormalVector(Num_Span, 1, Index), 0, Orientation_FaceVector(1))
        Set Spline_SectionOffset_Point(Num_Span, 2, Index, 1) = DPH.AddNewPointOnCurveFromPercent(Line_NormalVector(Num_Span, 2, Index), 0, Orientation_FaceVector(2))
        
        Set Spline_SectionOffset_Point(Num_Span, 1, Index, 2) = DPH.AddNewPointOnCurveFromPercent(Line_NormalVector(Num_Span, 1, Index), 1, Orientation_FaceVector(1))
        Set Spline_SectionOffset_Point(Num_Span, 2, Index, 2) = DPH.AddNewPointOnCurveFromPercent(Line_NormalVector(Num_Span, 2, Index), 1, Orientation_FaceVector(2))

        
        'Change Spline_Span And Spline_SectionOffset_Tip_x
        If nDeal = 1 Then
            Index = 1
        Else
            Index = Num_Divide
        End If
        

        Orientation = Orientation_ForSplit_ByX(Spline_SectionOffset_Tip_x, Point_2, DocumentObject, Extract_Cache)

        Set Spline_1 = DPH.AddNewHybridSplit(Spline_SectionOffset_Tip_x, Point_2, Orientation * (-1) ^ (nDeal + 1))

        Set Spline_Span(1, Index, 2) = DPH.AddNewJoin(Spline_Span(1, Index, 2), Spline_1)
        Set Spline_Span(2, Index, 2) = Spline_Span(1, Index, 2)


        Set Spline_SectionOffset_Tip_x = DPH.AddNewHybridSplit(Spline_SectionOffset_Tip_x, Point_2, -Orientation * (-1) ^ (nDeal + 1))
        
    Next nDeal

    
    'Hide
    DocumentObject.Selection.Add Extract_Cache
    DocumentObject.Selection.VisProperties.SetShow 1
    DocumentObject.Selection.Clear
    

    '-----------------------------------
    'Rotate Line_NormalVector
    '-----------------------------------
    Angle_Rotate_Trail = 20
    Angle_Rotate_Tip = 20

    
    'Trail
    For nSpan = 1 To Num_Span
        For nDu = 1 To 2
            
            If nSpan <> Num_Span Then
                Angle_Rotate_Local = Angle_Rotate_Trail
            Else
                Angle_Rotate_Local = Angle_Rotate_Trail
            End If
            
            D1 = Angle_Rotate_Local * Pi * LayerHeight_BlockSection(nSpan) / 180
            

            If nSpan <> Num_Span Then
                Set Spline_1 = Spline_SectionOffset_Trail_Total(nSpan)
            Else
                Set Spline_1 = DPH.AddNewJoin(Spline_LeadOrTrail_Outer(2, 1), Spline_LeadOrTrail_Outer(2, 2))
            End If
            
            If nDu = 1 Then
                Orientation = False
            Else
                Orientation = True
            End If
            
            
            Set Point_1 = Spline_SectionOffset_Point(nSpan, nDu, Num_Divide - 1, 1)
            
            Set Point_2 = DPH.AddNewPointOnCurveFromDistance(Spline_1, D1, Orientation)
            
            
            Set Line_1 = DPH.AddNewLinePtPt(Point_1, Point_2)
            
            Set Line_NormalVector(nSpan, nDu, Num_Divide - 1) = Line_1
                
            Set Spline_SectionOffset_Point(nSpan, nDu, Num_Divide - 1, 2) = Point_2
            
        Next nDu
    Next nSpan
    
               
    'Tip
    For nDivide = 3 To Num_Divide - 2
        For nDu = 1 To 2
            
            If nDivide <= 3 Then
            
                Angle_Rotate_Local = Angle_Rotate_Tip / 3 + (Divide(Num_Span, nDivide) - Divide(Num_Span, 2)) / (Divide(Num_Span, 4) - Divide(Num_Span, 2)) * (Angle_Rotate_Tip - Angle_Rotate_Tip / 3)
                
            Else
            
                Angle_Rotate_Local = Angle_Rotate_Tip
                
            End If
            
            D1 = Angle_Rotate_Local * Pi * LayerHeight_BlockSection(Num_Span) / 180
            
            
            If nDu = 1 Then
                Orientation = False
            Else
                Orientation = True
            End If
            
            Set Point_1 = Spline_SectionOffset_Point(Num_Span, nDu, nDivide, 1)

            Set Spline_1 = Spline_SectionOffset_Tip_y(nDivide)
            
            Set Point_2 = DPH.AddNewPointOnCurveFromDistance(Spline_1, D1, Orientation)
            
            
            Set Line_1 = DPH.AddNewLinePtPt(Point_1, Point_2)
            
            Set Line_NormalVector(Num_Span, nDu, nDivide) = Line_1
                
            Set Spline_SectionOffset_Point(Num_Span, nDu, nDivide, 2) = Point_2
                
        Next nDu
    Next nDivide
    
    
    'Change Spline_Span And Spline_SectionOffset_Tip_y
    For nDivide = 3 To Num_Divide - 2
        For nDu = 1 To 2
            
            If nDu = 1 Then
                Orientation = 1
            Else
                Orientation = -1
            End If
            
            
            Set Spline_1 = DPH.AddNewHybridSplit(Spline_SectionOffset_Tip_y(nDivide), Spline_SectionOffset_Point(Num_Span, nDu, nDivide, 2), Orientation)
            
            Set Spline_Span(nDu, nDivide, 2) = DPH.AddNewJoin(Spline_Span(nDu, nDivide, 2), Spline_1)
                        
                        
            Set Spline_SectionOffset_Tip_y(nDivide) = DPH.AddNewHybridSplit(Spline_SectionOffset_Tip_y(nDivide), Spline_SectionOffset_Point(Num_Span, nDu, nDivide, 2), -Orientation)

        Next nDu
    Next nDivide
    

    'Change Spline_Span
    For nBlock = 1 To Num_Section - 1
        For nDu = 1 To 2

            Set Spline_Span_Block(nDivide, nDu, 2, nBlock * 2) = DPH.AddNewLinePtPt(Spline_SectionOffset_Point(nBlock * 3 - 1, nDu, Num_Divide - 1, 2), _
                                                                                    Spline_SectionOffset_Point(nBlock * 3, nDu, Num_Divide - 1, 2))
            
        Next nDu
    Next nBlock
    
    
    For nBlock = 1 To Num_Section
         For nDu = 1 To 2

            If nBlock = 1 Then
                
                Set Spline_ForTangency_Inner = Direction_Y
                Set Spline_ForTangency_Outer = Spline_Span_Block(Num_Divide - 1, nDu, 2, nBlock * 2)
                
                
                Set Spline_Span_Block(Num_Divide - 1, nDu, 2, nBlock * 2 - 1) = DPH.AddNewSpline
            
                Spline_Span_Block(Num_Divide - 1, nDu, 2, nBlock * 2 - 1).AddPointWithConstraintFromCurve Spline_SectionOffset_Point((nBlock - 1) * 3 + 1, nDu, Num_Divide - 1, 2), Spline_ForTangency_Inner, 0.5, 1, 1
                                        
                Spline_Span_Block(Num_Divide - 1, nDu, 2, nBlock * 2 - 1).AddPointWithConstraintFromCurve Spline_SectionOffset_Point((nBlock - 1) * 3 + 2, nDu, Num_Divide - 1, 2), Spline_ForTangency_Outer, 0.5, 1, 1
            
                
            ElseIf nBlock = Num_Section Then
            
                Set Spline_ForTangency_Inner = Spline_Span_Block(Num_Divide - 1, nDu, 2, (nBlock - 1) * 2)
                Set Spline_ForTangency_Outer = DPH.AddNewLinePtPt(Spline_SectionOffset_Point(Num_Span - 1, nDu, Num_Divide - 1, 2), Spline_SectionOffset_Point(Num_Span, nDu, Num_Divide - 1, 2))
                
                
                Set Spline_Span_Block(Num_Divide - 1, nDu, 2, nBlock * 2 - 1) = DPH.AddNewSpline
            
                Spline_Span_Block(Num_Divide - 1, nDu, 2, nBlock * 2 - 1).AddPointWithConstraintFromCurve Spline_SectionOffset_Point((nBlock - 1) * 3, nDu, Num_Divide - 1, 2), Spline_ForTangency_Inner, 1, 1, 1
                                        
                Spline_Span_Block(Num_Divide - 1, nDu, 2, nBlock * 2 - 1).AddPointWithConstraintFromCurve Spline_SectionOffset_Point((nBlock - 1) * 3 + 1, nDu, Num_Divide - 1, 2), Spline_ForTangency_Outer, 1, 1, 1
                
            Else
            
                Set Spline_ForTangency_Inner = Spline_Span_Block(Num_Divide - 1, nDu, 2, (nBlock - 1) * 2)
                
                Set Spline_ForTangency_Mid = DPH.AddNewLinePtPt(Spline_SectionOffset_Point((nBlock - 1) * 3, nDu, Num_Divide - 1, 2), Spline_SectionOffset_Point((nBlock - 1) * 3 + 2, nDu, Num_Divide - 1, 2))
                
                Set Spline_ForTangency_Outer = Spline_Span_Block(Num_Divide - 1, nDu, 2, nBlock * 2)

                
                Set Spline_Span_Block(Num_Divide - 1, nDu, 2, nBlock * 2 - 1) = DPH.AddNewSpline
                
                    
                Spline_Span_Block(Num_Divide - 1, nDu, 2, nBlock * 2 - 1).AddPointWithConstraintFromCurve Spline_SectionOffset_Point((nBlock - 1) * 3, nDu, Num_Divide - 1, 2), Spline_ForTangency_Inner, 0.7, 1, 1
                   
                Spline_Span_Block(Num_Divide - 1, nDu, 2, nBlock * 2 - 1).AddPointWithConstraintFromCurve Spline_SectionOffset_Point((nBlock - 1) * 3 + 1, nDu, Num_Divide - 1, 2), Spline_ForTangency_Mid, 0.7, 1, 1
                   
                Spline_Span_Block(Num_Divide - 1, nDu, 2, nBlock * 2 - 1).AddPointWithConstraintFromCurve Spline_SectionOffset_Point((nBlock - 1) * 3 + 2, nDu, Num_Divide - 1, 2), Spline_ForTangency_Outer, 0.7, 1, 1

            End If

         Next nDu
    Next nBlock
    
    For nDu = 1 To 2
        
        Set Spline_Span(nDu, Num_Divide - 1, 2) = DPH.AddNewJoin(Spline_Span_Block(Num_Divide - 1, nDu, 2, 1), Spline_Span_Block(Num_Divide - 1, nDu, 2, 2))
                        
        For i = 3 To Num_Section * 2 - 1
            Spline_Span(nDu, Num_Divide - 1, 2).AddElement Spline_Span_Block(Num_Divide - 1, nDu, 2, i)
        Next i
            
    Next nDu
    

    'Change Spline_SectionOffset
    For nDu = 1 To 2

        Set Spline_Mid = DPH.AddNewSpline

        For nDivide = 3 To Num_Divide - 2

            Spline_Mid.AddPointWithConstraintExplicit Spline_SectionOffset_Point(Num_Span, nDu, nDivide, 2), Nothing, -1#, 1, Nothing, 0#

        Next nDivide


        Set Spline_Front = DPH.AddNewSpline

        Spline_Front.AddPointWithConstraintExplicit Spline_SectionOffset_Point(Num_Span, nDu, 2, 2), Nothing, -1#, 1, Nothing, 0#

        Spline_Front.AddPointWithConstraintFromCurve Spline_SectionOffset_Point(Num_Span, nDu, 3, 2), Spline_Mid, 1, 1, 1


        Set Spline_Behind = DPH.AddNewSpline

        Spline_Behind.AddPointWithConstraintExplicit Spline_SectionOffset_Point(Num_Span, nDu, Num_Divide - 1, 2), Nothing, -1#, 1, Nothing, 0#

        Spline_Behind.AddPointWithConstraintFromCurve Spline_SectionOffset_Point(Num_Span, nDu, Num_Divide - 2, 2), Spline_Mid, 1, -1, 1


        If nDu = 1 Then
            Orientation = -1
        Else
            Orientation = 1
        End If

        Set Spline_Lead = Spline_LeadOrTrail_Outer(1, nDu)

        Set Spline_Trail = DPH.AddNewHybridSplit(Spline_LeadOrTrail_Outer(2, nDu), Spline_SectionOffset_Point(Num_Span, nDu, Num_Divide - 1, 2), Orientation)


        Set Spline_SectionOffset(Num_Span, nDu) = DPH.AddNewJoin(Spline_Lead, Spline_Front)
        Spline_SectionOffset(Num_Span, nDu).AddElement Spline_Mid
        Spline_SectionOffset(Num_Span, nDu).AddElement Spline_Behind
        Spline_SectionOffset(Num_Span, nDu).AddElement Spline_Trail

    Next nDu
    

    '-----------------------------------
    'Smooth
    '-----------------------------------
    'Spline_SectionProject
    For nSpan = 1 To Num_Span
        
        If Orientation_LeadPoint(nSpan) <> 0 And Distance_LeadPoint(nSpan) <= 0.013 Then
        
            If Orientation_LeadPoint(nSpan) = -1 Then
                Deviation_1 = Deviation_Bridge
                Deviation_2 = 0.013
            Else
                Deviation_1 = 0.013
                Deviation_2 = Deviation_Bridge
            End If
            
        Else
        
            Deviation_1 = Deviation_Bridge
            Deviation_2 = Deviation_Bridge
            
        End If
        
        Set Spline_SectionProject(nSpan, 1) = DPH.AddNewCurveSmooth(Spline_SectionProject(nSpan, 1))
        Spline_SectionProject(nSpan, 1).SetMaximumDeviation Deviation_1
        Spline_SectionProject(nSpan, 1).CorrectionMode = 3
    
        Set Spline_SectionProject(nSpan, 2) = DPH.AddNewCurveSmooth(Spline_SectionProject(nSpan, 2))
        Spline_SectionProject(nSpan, 2).SetMaximumDeviation Deviation_2
        Spline_SectionProject(nSpan, 2).CorrectionMode = 3
        
    Next nSpan
    
    
    'Spline_SectionOffset
    For nSpan = 1 To Num_Span
        For nDu = 1 To 2
    
            Set Spline_SectionOffset(nSpan, nDu) = DPH.AddNewCurveSmooth(Spline_SectionOffset(nSpan, nDu))
            Spline_SectionOffset(nSpan, nDu).SetMaximumDeviation 0.005
            Spline_SectionOffset(nSpan, nDu).CorrectionMode = 3
       
        Next nDu
    Next nSpan
    
    
    'Spline_Span
    For nDu = 1 To 2
        For nDivide = 1 To Num_Divide
            For nIO = 1 To 2
                
                Set Spline_Span(nDu, nDivide, nIO) = DPH.AddNewCurveSmooth(Spline_Span(nDu, nDivide, nIO))
                
                If (nDivide = 1 Or nDivide = Num_Divide) And nIO = 1 Then
                
                    Span_Half = Data_SectionPoint(Num_Section * Num_PointPerSpline, 2) - Data_SectionPoint(Num_PointPerSpline, 2)
                    
                    If Span_Half < 2500 Then
                        D = 0.011
                    Else
                        D = 0.011 + 0.03 * (Span_Half - 2500) / (5000 - 2500)
                        
                        If D > 0.041 Then
                            D = 0.041
                        End If
                    End If
                    
                    Spline_Span(nDu, nDivide, nIO).SetMaximumDeviation Deviation_Bridge + D
                    
                Else
                    Spline_Span(nDu, nDivide, nIO).SetMaximumDeviation Deviation_Bridge + 0.001
                End If
                
                Spline_Span(nDu, nDivide, nIO).CorrectionMode = 3

            Next nIO
        Next nDivide
    Next nDu
            
            
    'Spline_SectionProject_Tip_x
    Set Spline_SectionProject_Tip_x = DPH.AddNewCurveSmooth(Spline_SectionProject_Tip_x)
    Spline_SectionProject_Tip_x.SetMaximumDeviation 0.001
    Spline_SectionProject_Tip_x.CorrectionMode = 3
    
    
    'Spline_SectionProject_Tip_y
    For nDivide = 3 To Num_Divide - 2
        
        Set Spline_SectionProject_Tip_y(nDivide) = DPH.AddNewCurveSmooth(Spline_SectionProject_Tip_y(nDivide))
        Spline_SectionProject_Tip_y(nDivide).SetMaximumDeviation 0.002
        Spline_SectionProject_Tip_y(nDivide).CorrectionMode = 3
        
    Next nDivide
    
    
    'Spline_SectionOffset_Tip_x
    Set Spline_SectionOffset_Tip_x = DPH.AddNewCurveSmooth(Spline_SectionOffset_Tip_x)
    Spline_SectionOffset_Tip_x.SetMaximumDeviation 0.001
    Spline_SectionOffset_Tip_x.CorrectionMode = 3
    
    
    'Spline_SectionOffset_Tip_y
    For nDivide = 3 To Num_Divide - 2
        
        Set Spline_SectionOffset_Tip_y(nDivide) = DPH.AddNewCurveSmooth(Spline_SectionOffset_Tip_y(nDivide))
        Spline_SectionOffset_Tip_y(nDivide).SetMaximumDeviation 0.001
        Spline_SectionOffset_Tip_y(nDivide).CorrectionMode = 3

    Next nDivide


    '-----------------------------------
    'Extract
    '-----------------------------------
    'Spline_SectionOffset_Point
    Set Extract_Spline_SectionOffset_Point = DPH.AddNewExtractMulti(EmptyObject)
    Set Extract_Spline_SectionOffset_Point_Repeat = DPH.AddNewExtractMulti(EmptyObject)
                
    For nSpan = 1 To Num_Span
        For nDu = 1 To 2
            For nDivide = 1 To Num_Divide
                For nIO = 1 To 2
                    
                    nSection = Int(nSpan / 3) + 1
                    
                    If Not IsInArray(nSection, Index_NonActSection_ICEM) Then
                    
                        If Not ((nDu = 2 And nDivide = 1) Or (nDu = 2 And nDivide = Num_Divide)) Then
                        
                            Extract_Spline_SectionOffset_Point.AddConstraintTolerant Spline_SectionOffset_Point(nSpan, nDu, nDivide, nIO), 3, False, False, 0.1, 0.5, 0.98, 1
                            Extract_Spline_SectionOffset_Point.SetElement 1, Spline_SectionOffset_Point(nSpan, nDu, nDivide, nIO)
                        
                        Else
                            
                            Extract_Spline_SectionOffset_Point_Repeat.AddConstraintTolerant Spline_SectionOffset_Point(nSpan, nDu, nDivide, nIO), 3, False, False, 0.1, 0.5, 0.98, 1
                            Extract_Spline_SectionOffset_Point_Repeat.SetElement 1, Spline_SectionOffset_Point(nSpan, nDu, nDivide, nIO)
                        
                        End If
                    
                    End If
                                  
                Next nIO
            Next nDivide
        Next nDu
    Next nSpan
    
    WorkObject.InsertHybridShape Extract_Spline_SectionOffset_Point
    WorkObject.InsertHybridShape Extract_Spline_SectionOffset_Point_Repeat
    
    Extract_Spline_SectionOffset_Point.Name = "Spline_SectionOffset_Point"
    Extract_Spline_SectionOffset_Point_Repeat.Name = "Spline_SectionOffset_Point_Repeat"
    
    
    'Spline_SectionOffset_Tip_Point
    Set Extract_Spline_SectionOffset_Tip_Point = DPH.AddNewExtractMulti(EmptyObject)
                
    For nTip = 1 To Num_Divide - 4
        For nIO = 1 To 2
        
            Extract_Spline_SectionOffset_Tip_Point.AddConstraintTolerant Spline_SectionOffset_Tip_Point(nTip, nIO), 3, False, False, 0.1, 0.5, 0.98, 1
            Extract_Spline_SectionOffset_Tip_Point.SetElement 1, Spline_SectionOffset_Tip_Point(nTip, nIO)
        
        Next nIO
    Next nTip
    
    WorkObject.InsertHybridShape Extract_Spline_SectionOffset_Tip_Point
    
    Extract_Spline_SectionOffset_Tip_Point.Name = "Spline_SectionOffset_Tip_Point"
    
    
    'Spline_SectionProject
    Set Extract_Spline_SectionProject = DPH.AddNewExtractMulti(EmptyObject)
                
    For nSpan = 1 To Num_Span
        For nDu = 1 To 2
            
            nSection = Int(nSpan / 3) + 1
                    
            If Not IsInArray(nSection, Index_NonActSection_ICEM) Then
            
                Extract_Spline_SectionProject.AddConstraintTolerant Spline_SectionProject(nSpan, nDu), 3, False, False, 0.1, 0.5, 0.98, 1
                Extract_Spline_SectionProject.SetElement 1, Spline_SectionProject(nSpan, nDu)
            
            End If
            
        Next nDu
    Next nSpan
    
    WorkObject.InsertHybridShape Extract_Spline_SectionProject
    
    Extract_Spline_SectionProject.Name = "Spline_SectionProject"
    

    'Spline_SectionOffset
    Set Extract_Spline_SectionOffset = DPH.AddNewExtractMulti(EmptyObject)
                
    For nSpan = 1 To Num_Span
        For nDu = 1 To 2
            
            nSection = Int(nSpan / 3) + 1
                    
            If Not IsInArray(nSection, Index_NonActSection_ICEM) Then
            
                Extract_Spline_SectionOffset.AddConstraintTolerant Spline_SectionOffset(nSpan, nDu), 3, False, False, 0.1, 0.5, 0.98, 1
                Extract_Spline_SectionOffset.SetElement 1, Spline_SectionOffset(nSpan, nDu)
            
            End If
            
        Next nDu
    Next nSpan
    
    WorkObject.InsertHybridShape Extract_Spline_SectionOffset
    
    Extract_Spline_SectionOffset.Name = "Spline_SectionOffset"
    
    
    'Line_NormalVector
    Set Extract_Line_NormalVector = DPH.AddNewExtractMulti(EmptyObject)
                
    For nSpan = 1 To Num_Span
        For nDu = 1 To 2
            For nDivide = 1 To Num_Divide
                
                nSection = Int(nSpan / 3) + 1
                    
                If Not IsInArray(nSection, Index_NonActSection_ICEM) Then
                
                    If Not ((nDu = 2 And nDivide = 1) Or (nDu = 2 And nDivide = Num_Divide)) Then
                    
                        Extract_Line_NormalVector.AddConstraintTolerant Line_NormalVector(nSpan, nDu, nDivide), 3, False, False, 0.1, 0.5, 0.98, 1
                        Extract_Line_NormalVector.SetElement 1, Line_NormalVector(nSpan, nDu, nDivide)
                        
                    End If
                
                End If
        
            Next nDivide
        Next nDu
    Next nSpan
    
    WorkObject.InsertHybridShape Extract_Line_NormalVector
    
    Extract_Line_NormalVector.Name = "Line_NormalVector"
    
    
    'Spline_Span
    Set Extract_Spline_Span = DPH.AddNewExtractMulti(EmptyObject)
                
    For nDu = 1 To 2
        For nDivide = 1 To Num_Divide
            For nIO = 1 To 2
                
                If Not ((nDu = 2 And nDivide = 1) Or (nDu = 2 And nDivide = Num_Divide)) Then
                
                    Extract_Spline_Span.AddConstraintTolerant Spline_Span(nDu, nDivide, nIO), 3, False, False, 0.1, 0.5, 0.98, 1
                    Extract_Spline_Span.SetElement 1, Spline_Span(nDu, nDivide, nIO)
                    
                End If
        
            Next nIO
        Next nDivide
    Next nDu
    
    WorkObject.InsertHybridShape Extract_Spline_Span
    
    Extract_Spline_Span.Name = "Spline_Span"


    'Spline_Tip_xyz
    Set Extract_Spline_Tip_xyz = DPH.AddNewExtractMulti(EmptyObject)
                        
    Extract_Spline_Tip_xyz.AddConstraintTolerant Spline_SectionProject_Tip_x, 3, False, False, 0.1, 0.5, 0.98, 1
    Extract_Spline_Tip_xyz.SetElement 1, Spline_SectionProject_Tip_x
    
    Extract_Spline_Tip_xyz.AddConstraintTolerant Spline_SectionOffset_Tip_x, 3, False, False, 0.1, 0.5, 0.98, 1
    Extract_Spline_Tip_xyz.SetElement 1, Spline_SectionOffset_Tip_x
                    
    For nDivide = 3 To Num_Divide - 2

        Extract_Spline_Tip_xyz.AddConstraintTolerant Spline_SectionProject_Tip_y(nDivide), 3, False, False, 0.1, 0.5, 0.98, 1
        Extract_Spline_Tip_xyz.SetElement 1, Spline_SectionProject_Tip_y(nDivide)
        
        Extract_Spline_Tip_xyz.AddConstraintTolerant Spline_SectionOffset_Tip_y(nDivide), 3, False, False, 0.1, 0.5, 0.98, 1
        Extract_Spline_Tip_xyz.SetElement 1, Spline_SectionOffset_Tip_y(nDivide)
        
        Extract_Spline_Tip_xyz.AddConstraintTolerant Line_NormalVector_Tip(nDivide), 3, False, False, 0.1, 0.5, 0.98, 1
        Extract_Spline_Tip_xyz.SetElement 1, Line_NormalVector_Tip(nDivide)
        
    Next nDivide
    
    WorkObject.InsertHybridShape Extract_Spline_Tip_xyz
    
    Extract_Spline_Tip_xyz.Name = "Spline_Tip_xyz"
    
    
    'Hide
    DocumentObject.Selection.Add Extract_Spline_SectionOffset_Point_Repeat
    
    DocumentObject.Selection.VisProperties.SetShow 1
    DocumentObject.Selection.Clear
    
        
    '-----------------------------------
    'Return
    '-----------------------------------
    ReDim ICEM_Subline_01.Dihedral(1 To Num_Span) As Double
    For nSpan = 1 To Num_Span
            
        ICEM_Subline_01.Dihedral(nSpan) = Dihedral(nSpan)
        
    Next nSpan
    
    
    ICEM_Subline_01.Num_Divide = Num_Divide
    
    
    ICEM_Subline_01.Num_Span = Num_Span
    
    
    ReDim ICEM_Subline_01.Span_BlockSection(1 To Num_Span) As Double
    For nSpan = 1 To Num_Span

        ICEM_Subline_01.Span_BlockSection(nSpan) = Span_BlockSection(nSpan)

    Next nSpan
    
    ReDim ICEM_Subline_01.SpanSLength_BlockSection(1 To Num_Span) As Double
    For nSpan = 1 To Num_Span
        
        ICEM_Subline_01.SpanSLength_BlockSection(nSpan) = SpanSLength_BlockSection(nSpan)
            
    Next nSpan
    
    
    ReDim ICEM_Subline_01.LayerHeight_BlockSection(1 To Num_Span) As Double
    For nSpan = 1 To Num_Span
            
        ICEM_Subline_01.LayerHeight_BlockSection(nSpan) = LayerHeight_BlockSection(nSpan)

    Next nSpan
    
    
    ReDim ICEM_Subline_01.Length_Chord_BlockSection(1 To Num_Span) As Double
    For nSpan = 1 To Num_Span
            
        ICEM_Subline_01.Length_Chord_BlockSection(nSpan) = Length_Chord_BlockSection(nSpan)

    Next nSpan
    
    
    ReDim ICEM_Subline_01.Spline_SectionOffset_Point(1 To Num_Span, 1 To 2, 1 To 11, 1 To 2)
    For nSpan = 1 To Num_Span
        For nDu = 1 To 2
            For nDivide = 1 To Num_Divide
                For nIO = 1 To 2
                
                    Set ICEM_Subline_01.Spline_SectionOffset_Point(nSpan, nDu, nDivide, nIO) = Spline_SectionOffset_Point(nSpan, nDu, nDivide, nIO)
                    
                Next nIO
            Next nDivide
        Next nDu
    Next nSpan
    
    
    ReDim ICEM_Subline_01.Spline_SectionOffset_Tip_Point(1 To Num_Divide - 4, 1 To 2)
    For nTip = 1 To Num_Divide - 4
        For nIO = 1 To 2
                        
            Set ICEM_Subline_01.Spline_SectionOffset_Tip_Point(nTip, nIO) = Spline_SectionOffset_Tip_Point(nTip, nIO)
        
        Next nIO
    Next nTip
    
    
    ReDim ICEM_Subline_01.Spline_SectionProject(1 To Num_Span, 1 To 2)
    For nSpan = 1 To Num_Span
        For nDu = 1 To 2
        
            Set ICEM_Subline_01.Spline_SectionProject(nSpan, nDu) = Spline_SectionProject(nSpan, nDu)
            
        Next nDu
    Next nSpan
    
    
    ReDim ICEM_Subline_01.Spline_SectionOffset(1 To Num_Span, 1 To 2)
    For nSpan = 1 To Num_Span
        For nDu = 1 To 2
        
            Set ICEM_Subline_01.Spline_SectionOffset(nSpan, nDu) = Spline_SectionOffset(nSpan, nDu)
            
        Next nDu
    Next nSpan
    
    
    ReDim ICEM_Subline_01.Line_NormalVector(1 To Num_Span, 1 To 2, 1 To 11)
    For nSpan = 1 To Num_Span
        For nDu = 1 To 2
            For nDivide = 1 To Num_Divide
            
                Set ICEM_Subline_01.Line_NormalVector(nSpan, nDu, nDivide) = Line_NormalVector(nSpan, nDu, nDivide)
                
            Next nDivide
        Next nDu
    Next nSpan
    
    
    ReDim ICEM_Subline_01.Spline_Span(1 To 2, 1 To 11, 1 To 2)
    For nDu = 1 To 2
        For nDivide = 1 To Num_Divide
            For nIO = 1 To 2

                Set ICEM_Subline_01.Spline_Span(nDu, nDivide, nIO) = Spline_Span(nDu, nDivide, nIO)
        
            Next nIO
        Next nDivide
    Next nDu
    
    
    Set ICEM_Subline_01.Spline_SectionProject_Tip_x = Spline_SectionProject_Tip_x
    
    
    ReDim ICEM_Subline_01.Spline_SectionProject_Tip_y(3 To Num_Divide - 2)
    For nDivide = 3 To Num_Divide - 2

        Set ICEM_Subline_01.Spline_SectionProject_Tip_y(nDivide) = Spline_SectionProject_Tip_y(nDivide)
        
    Next nDivide
    
    
    Set ICEM_Subline_01.Spline_SectionOffset_Tip_x = Spline_SectionOffset_Tip_x
    
    
    ReDim ICEM_Subline_01.Spline_SectionOffset_Tip_y(3 To Num_Divide - 2)
    For nDivide = 3 To Num_Divide - 2

        Set ICEM_Subline_01.Spline_SectionOffset_Tip_y(nDivide) = Spline_SectionOffset_Tip_y(nDivide)

    Next nDivide
    
    
    ReDim ICEM_Subline_01.Line_NormalVector_Tip(3 To Num_Divide - 2)
    For nDivide = 3 To Num_Divide - 2

        Set ICEM_Subline_01.Line_NormalVector_Tip(nDivide) = Line_NormalVector_Tip(nDivide)
        
    Next nDivide
        
End Function

   
'*****************************
'ICEM_Subline_23
'*****************************
Function ICEM_Subline_23(ByVal DocumentObject As Object, _
                         ByRef Entity_ICEM_FluidAndBOI As Type_ICEM_FluidAndBOI, _
                         ByRef Entity_ICEM_Subline_01 As Type_ICEM_Subline_01, _
                         ByVal Data_SectionPoint As Variant, ByVal Num_Section As Integer, ByVal Num_PointPerSpline As Integer, _
                         ByVal MAC_Length As Double, ByVal MAC_x As Double, _
                         ByVal Diameter_Fillet As Double, ByVal Rate_Fluid As Double, ByVal Rate_BOI_Fluid_MAC As Double, ByVal Rate_BOI_Fluid_Span As Double, _
                         ByVal Index_NonActSection_ICEM As Variant) _
                         As Type_ICEM_Subline_23

    'CreateOrderGeometry
    Set WorkObject = DocumentObject.Part.OrderedGeometricalSets.Add()
    DocumentObject.Part.OrderedGeometricalSets.Item(6).Name = "ICEM_Subline_23"
    
    
    Set DPH = DocumentObject.Part.HybridShapeFactory
    
    Num_Spline = Num_Section * 2
    
    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Define
    '-----------------------------------
    Rate_FrontBack = 1
    
    
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
        
        
    'Point_Ref
    Dim Point_Ref(1 To 3, 1 To 2) As Object
    
    X1 = Length_Chord(1) / 2
    Y1 = 0
    Z1 = 0
    
    Set Point_Ref(1, 1) = DPH.AddNewPointCoord(X1, Y1, Z1)
    
    X1 = Length_Chord(1) / 2 - Entity_ICEM_FluidAndBOI.Radius_BOI_Fluid_BasedMAC
    Y1 = 0
    Z1 = 0
    
    Set Point_Ref(2, 1) = DPH.AddNewPointCoord(X1, Y1, Z1)

    X1 = Length_Chord(1) / 2
    Y1 = 0
    Z1 = Entity_ICEM_FluidAndBOI.Radius_BOI_Fluid_BasedMAC
    
    Set Point_Ref(3, 1) = DPH.AddNewPointCoord(X1, Y1, Z1)
    
    
    X1 = Length_Chord(1) / 2
    Y1 = 0
    Z1 = 0
    
    Set Point_Ref(1, 2) = DPH.AddNewPointCoord(X1, Y1, Z1)
    
    X1 = Length_Chord(1) / 2 - Entity_ICEM_FluidAndBOI.Radius_Fluid
    Y1 = 0
    Z1 = 0
    
    Set Point_Ref(2, 2) = DPH.AddNewPointCoord(X1, Y1, Z1)

    X1 = Length_Chord(1) / 2
    Y1 = 0
    Z1 = Entity_ICEM_FluidAndBOI.Radius_Fluid
    
    Set Point_Ref(3, 2) = DPH.AddNewPointCoord(X1, Y1, Z1)
    
    
    'Surface_ForProject
    Dim Surface_ForProject(1 To 2) As Object
    
    Set Surface_ForProject(1) = Entity_ICEM_FluidAndBOI.Surface_BOI_Fluid
    Set Surface_ForProject(2) = Entity_ICEM_FluidAndBOI.Surface_Fluid
    
    
    'Divide
    Divide = Array(999, 1, 2, 3, 4, 5, 6, 7, 8, 9, 10, 11)
    Num_Divide = UBound(Divide) - LBound(Divide)
    
    
    'Span
    Dim Span() As Integer
    
    ReDim Span(1 To Num_Section + 1) As Integer
    
    For nSection = 1 To Num_Section
        
        If nSection < Num_Section Then
        
            Span(nSection) = (nSection - 1) * 3 + 1
        
        Else
        
            Span(Num_Section) = (nSection - 1) * 3
            Span(Num_Section + 1) = (nSection - 1) * 3 + 1
        
        End If
    
    Next nSection

    Num_Span = UBound(Span) - LBound(Span) + 1
    
    
    '-----------------------------------
    'Create Spline_Tip & Root
    '-----------------------------------
    Dim Spline_Tip_Point(1 To 2, 1 To 7) As Object
    Dim Spline_Root_Point(1 To 2, 1 To 7) As Object
    
    Dim Spline_Tip_Part(1 To 2, 1 To 4) As Object
    Dim Spline_Root_Part(1 To 2, 1 To 4) As Object
    
    
    'Create Spline_Tip_Point
    Span_Half = Data_SectionPoint(Num_Section * Num_PointPerSpline, 2) - Data_SectionPoint(Num_PointPerSpline, 2)
    
    SweepbackAngle_Lead = Atn((Data_SectionPoint((Num_Section - 1) * Num_PointPerSpline + 1, 1) - Data_SectionPoint(1, 1)) / Span_Half) * 57.3

    SweepbackAngle_Trail = Atn((Data_SectionPoint(Num_Section * Num_PointPerSpline, 1) - Data_SectionPoint(Num_PointPerSpline, 1)) / Span_Half) * 57.3
    
    SweepbackAngle_Mid = (SweepbackAngle_Lead + SweepbackAngle_Trail) / 2
    
    If SweepbackAngle_Mid < 0 Then
        SweepbackAngle_Mid = 0
    End If
    
    
    Angle_x_Basic = 30
    
    If SweepbackAngle_Mid <= 50 Then
        Angle_x_Rotate = SweepbackAngle_Mid / 50 * 30
    Else
        Angle_x_Rotate = 30
    End If
    

    K_x = Cos(Angle_x_Basic / 57.3)
    
    If Rate_FrontBack = 1 Then
    
        K_y = 0.1565 * K_x
        
        K_y_Mid = K_y * 2.1
        
    ElseIf Rate_FrontBack = 2 Then
    
        K_y = 0.305 * K_x
        
        K_y_Mid = K_y * 1.5
        
    End If
    
    Radius_BOI_Fluid_BasedMAC = Entity_ICEM_FluidAndBOI.Radius_BOI_Fluid_BasedMAC
    Radius_Fluid = Entity_ICEM_FluidAndBOI.Radius_Fluid
    
    For nIO = 1 To 2
        
        If nIO = 1 Then
            K_Scale = 1
        Else
            K_Scale = Radius_Fluid / Radius_BOI_Fluid_BasedMAC
        End If
    
        
        nPoint = 1
        
        For nDu = 1 To 2
            For i = 1 To 3
            
                nPoint = nPoint + 1
                
                If i = 1 Then
                
                    X1 = Length_Chord(1) / 2 + Radius_BOI_Fluid_BasedMAC * Sin((-Angle_x_Basic * (-1) ^ (nDu + 1) + Angle_x_Rotate) / 57.3) * K_Scale
                    
                ElseIf i = 2 Then
                
                    X1 = Length_Chord(1) / 2 + Radius_BOI_Fluid_BasedMAC * Sin(Angle_x_Rotate / 57.3) * K_Scale
                    
                ElseIf i = 3 Then
                
                    X1 = Length_Chord(1) / 2 + Radius_BOI_Fluid_BasedMAC * Sin((Angle_x_Basic * (-1) ^ (nDu + 1) + Angle_x_Rotate) / 57.3) * K_Scale
                    
                End If
                
                Y1 = 0
                
                If i = 2 Then
                    Z1 = Radius_BOI_Fluid_BasedMAC * K_y_Mid * K_Scale * (-1) ^ nDu
                Else
                    Z1 = Radius_BOI_Fluid_BasedMAC * K_y * K_Scale * (-1) ^ nDu
                End If
                
                
                Set Point_1 = DPH.AddNewPointCoord(X1, Y1, Z1)
                
                Set Spline_Tip_Point(nIO, nPoint) = DPH.AddNewProject(Point_1, Surface_ForProject(nIO))
                Spline_Tip_Point(nIO, nPoint).Normal = False
                Spline_Tip_Point(nIO, nPoint).Direction = Direction_Y
                
                'WorkObject.InsertHybridShape Spline_Tip_Point(nIO, nPoint)

            Next i
        Next nDu
                   
        Set Spline_Tip_Point(nIO, 1) = Spline_Tip_Point(nIO, 7)
        
    Next nIO
    

    'Create Spline_Root_Point
    For nIO = 1 To 2
    
        Set Spline_1 = DPH.AddNewIntersection(Surface_ForProject(nIO), PLANE_ZX)
        
        
        nPoint = 1
        
        For nDu = 1 To 2
            For i = 1 To 3
                
                nPoint = nPoint + 1
                
                If Rate_FrontBack = 1 Then
                
                    K_Total = Array(999, 1 / 20, 5 / 20, 9 / 20)
                    
                ElseIf Rate_FrontBack = 2 Then
                
                    K_Total = Array(999, 2 / 24, 6 / 24, 10 / 24)
                    
                End If
                
                If i = 1 Then
                    K = 1 / 2 * (nDu - 1) - K_Total(i) * (-1) ^ nDu
                ElseIf i = 2 Then
                    K = 1 / 2 * (nDu - 1) - K_Total(i) * (-1) ^ nDu
                ElseIf i = 3 Then
                    K = 1 / 2 * (nDu - 1) - K_Total(i) * (-1) ^ nDu
                End If
    
                If nDu = 1 Then
                    Orientation = True
                Else
                    Orientation = False
                End If
    
                
                Set Spline_Root_Point(nIO, nPoint) = DPH.AddNewPointOnCurveWithReferenceFromPercent(Spline_1, Point_Ref(2, nIO), K, Orientation)
                
                'WorkObject.InsertHybridShape Spline_Root_Point(nIO, nPoint)
                
            Next i
        Next nDu
        
        Set Spline_Root_Point(nIO, 1) = Spline_Root_Point(nIO, 7)
        
    Next nIO
    
    
    'Create Spline_Tip & Spline_Root
    Index = Array(999, 1, 2, 4, 5)
    
    For nIO = 1 To 2
        For nLine = 1 To 4

            Set Spline_Tip_Part(nIO, nLine) = DPH.AddNewSpline
            Set Spline_Root_Part(nIO, nLine) = DPH.AddNewPolyline
            
            Spline_Tip_Part(nIO, nLine).AddPointWithConstraintExplicit Spline_Tip_Point(nIO, Index(nLine)), Nothing, -1#, 1, Nothing, 0#
            Spline_Tip_Part(nIO, nLine).AddPointWithConstraintExplicit Spline_Tip_Point(nIO, Index(nLine) + 1), Nothing, -1#, 1, Nothing, 0#
            If nLine = 2 Or nLine = 4 Then
                Spline_Tip_Part(nIO, nLine).AddPointWithConstraintExplicit Spline_Tip_Point(nIO, Index(nLine) + 2), Nothing, -1#, 1, Nothing, 0#
            End If
            
            
            Spline_Root_Part(nIO, nLine).InsertElement Spline_Root_Point(nIO, Index(nLine)), 1
            Spline_Root_Part(nIO, nLine).InsertElement Spline_Root_Point(nIO, Index(nLine) + 1), 2
            If nLine = 2 Or nLine = 4 Then
                Spline_Root_Part(nIO, nLine).InsertElement Spline_Root_Point(nIO, Index(nLine) + 2), 3
            End If
        
        Next nLine
    Next nIO
    
    
    For nIO = 1 To 2
        For nLine = 1 To 4
        
            Set Spline_Tip_Part(nIO, nLine) = DPH.AddNewProject(Spline_Tip_Part(nIO, nLine), Surface_ForProject(nIO))
            Spline_Tip_Part(nIO, nLine).Normal = True
            
            
            If nLine = 1 Or nLine = 3 Then
                
                If nLine = 1 Then
                
                    Set Surface_1 = DPH.AddNewHybridSplit(Surface_ForProject(nIO), PLANE_YZ, -1)
                
                ElseIf nLine = 3 Then
                    
                    Set Surface_1 = DPH.AddNewHybridSplit(Surface_ForProject(nIO), PLANE_YZ, 1)
                
                End If
                
                Set Spline_Root_Part(nIO, nLine) = DPH.AddNewProject(Spline_Root_Part(nIO, nLine), Surface_1)
                Spline_Root_Part(nIO, nLine).Normal = False
                Spline_Root_Part(nIO, nLine).Direction = Direction_X
                    
            ElseIf nLine = 2 Or nLine = 4 Then
                
                If nLine = 2 Then
                
                    Set Surface_1 = DPH.AddNewHybridSplit(Surface_ForProject(nIO), PLANE_XY, -1)
                
                ElseIf nLine = 4 Then
                    
                    Set Surface_1 = DPH.AddNewHybridSplit(Surface_ForProject(nIO), PLANE_XY, 1)
                
                End If
                
                Set Spline_Root_Part(nIO, nLine) = DPH.AddNewProject(Spline_Root_Part(nIO, nLine), Surface_1)
                Spline_Root_Part(nIO, nLine).Normal = False
                Spline_Root_Part(nIO, nLine).Direction = Direction_Z
            
            End If
            
            
            'WorkObject.InsertHybridShape Spline_Tip_Part(nIO, nLine)
            'WorkObject.InsertHybridShape Spline_Root_Part(nIO, nLine)
            
        Next nLine
    Next nIO
        
    
    '-----------------------------------
    'Create Spline_Tran_y
    '-----------------------------------
    Dim Spline_Tran_y(1 To 2, 1 To 11, 1 To 2) As Object

    For nIO = 1 To 2
        For nDu = 1 To 2
            For nDivide = 1 To Num_Divide

                If nDivide = 1 Then

                    Set Point_1 = DPH.AddNewPointOnCurveFromPercent(Spline_Root_Part(nIO, 1), 0.5, False)
                    Set Point_2 = DPH.AddNewPointOnCurveFromPercent(Spline_Tip_Part(nIO, 1), 0.5, False)

                ElseIf nDivide = Num_Divide Then

                    Set Point_1 = DPH.AddNewPointOnCurveFromPercent(Spline_Root_Part(nIO, 3), 0.5, False)
                    Set Point_2 = DPH.AddNewPointOnCurveFromPercent(Spline_Tip_Part(nIO, 3), 0.5, False)

                Else
                    
                    K = (nDivide - 2) / (Num_Divide - 3)
                    
                    If nDu = 1 Then
                    
                        Set Point_1 = DPH.AddNewPointOnCurveFromPercent(Spline_Root_Part(nIO, 2), K, False)
                        Set Point_2 = DPH.AddNewPointOnCurveFromPercent(Spline_Tip_Part(nIO, 2), K, False)
                        
                        If nDivide > 2 And nDivide < Num_Divide - 1 Then
                            
                            Set Point_3 = DPH.AddNewPointOnCurveFromPercent(Spline_Tip_Part(nIO, 4), K, True)
                            Set Point_4 = DPH.AddNewPointOnCurveFromPercent(Spline_Root_Part(nIO, 4), K, True)
                            
                        End If
                    
                    Else
                    
                        Set Point_1 = DPH.AddNewPointOnCurveFromPercent(Spline_Root_Part(nIO, 4), K, True)
                        Set Point_2 = DPH.AddNewPointOnCurveFromPercent(Spline_Tip_Part(nIO, 4), K, True)
                        
                        If nDivide > 2 And nDivide < Num_Divide - 1 Then
                            
                            Set Point_3 = DPH.AddNewPointOnCurveFromPercent(Spline_Tip_Part(nIO, 2), K, False)
                            Set Point_4 = DPH.AddNewPointOnCurveFromPercent(Spline_Root_Part(nIO, 2), K, False)
                            
                        End If
                    
                    End If
                
                End If

                
                If nDivide <= 2 Or nDivide >= Num_Divide - 1 Then
                
                    Set Spline_Tran_y(nDu, nDivide, nIO) = DPH.AddNewSpline
    
                    Spline_Tran_y(nDu, nDivide, nIO).AddPointWithConstraintFromCurve Point_1, Direction_Y, 1, 1, 1
                    Spline_Tran_y(nDu, nDivide, nIO).AddPointWithConstraintExplicit Point_2, Nothing, -1#, 1, Nothing, 0#
                    
                Else
                    
                    Set Spline_1 = DPH.AddNewSpline
    
                    Spline_1.AddPointWithConstraintFromCurve Point_1, Direction_Y, 1, 1, 1
                    Spline_1.AddPointWithConstraintExplicit Point_2, Nothing, -1#, 1, Nothing, 0#
                    Spline_1.AddPointWithConstraintExplicit Point_3, Nothing, -1#, 1, Nothing, 0#
                    Spline_1.AddPointWithConstraintFromCurve Point_4, Direction_Y, 1, -1, 1
                    
                    If nDu = 1 Then
                        Set Spline_Tran_y(nDu, nDivide, nIO) = DPH.AddNewHybridSplit(Spline_1, Spline_Tip_Part(nIO, 2), 1)
                    Else
                        Set Spline_Tran_y(nDu, nDivide, nIO) = DPH.AddNewHybridSplit(Spline_1, Spline_Tip_Part(nIO, 4), 1)
                    End If
                    
                End If


                Set Spline_Tran_y(nDu, nDivide, nIO) = DPH.AddNewProject(Spline_Tran_y(nDu, nDivide, nIO), Surface_ForProject(nIO))
                Spline_Tran_y(nDu, nDivide, nIO).Normal = True

                'WorkObject.InsertHybridShape Spline_Tran_y(nDU, nDivide, nIO)

            Next nDivide
        Next nDu
    Next nIO
    
    
    '-----------------------------------
    'Create Spline_Tran_x
    '-----------------------------------
    Dim K_Adjust_Tip(1 To 11) As Double
    Dim K_SpanSLength(1 To 11) As Double
    
    Dim Spline_Tran_x_Total(1 To MaxNum_Array, 1 To 2) As Object
    Dim Spline_Tran_x(1 To MaxNum_Array, 1 To 2, 1 To 2) As Object
        
        
    'Create Spline_Tran_x_Total
    DSLength = (Entity_ICEM_Subline_01.SpanSLength_BlockSection(Num_Section * 3 - 2) - Entity_ICEM_Subline_01.SpanSLength_BlockSection(Num_Section * 3 - 2 - 2)) * 2
    
    SpanSLength_Half_Adjust = Entity_ICEM_Subline_01.SpanSLength_BlockSection(Num_Section * 3 - 2 - 2) + DSLength
    
    
    K_Adjust_Tip_Up = 0.93
    
    If SweepbackAngle_Mid <= 50 Then
    
        K_Adjust_Tip_Low = K_Adjust_Tip_Up - SweepbackAngle_Mid / 50 * (K_Adjust_Tip_Up - 0.8)
        
    Else
        
        K_Adjust_Tip_Low = 0.83
        
    End If
    
    
    For nDivide = 1 To Num_Divide
    
        If nDivide = 1 Then
        
            K_Adjust_Tip(nDivide) = K_Adjust_Tip_Up
            
        ElseIf nDivide = 11 Then
        
            K_Adjust_Tip(nDivide) = K_Adjust_Tip_Low
            
        Else
        
            K_Adjust_Tip(nDivide) = K_Adjust_Tip_Up - (nDivide - 2) / 8 * (K_Adjust_Tip_Up - K_Adjust_Tip_Low)
            
        End If
        
    Next nDivide
    
                        
    
    For nSpan = 1 To Num_Span
        For nIO = 1 To 2
            
            For nDivide = 1 To Num_Divide
            
                If Span(nSpan) <= Num_Section * 3 - 2 - 2 Then
                    
                    K_SpanSLength(nDivide) = Entity_ICEM_Subline_01.SpanSLength_BlockSection(Span(nSpan)) / SpanSLength_Half_Adjust * K_Adjust_Tip(nDivide)
                            
                ElseIf Span(nSpan) = Num_Section * 3 - 2 - 1 Then
    
                    K_SpanSLength(nDivide) = (Entity_ICEM_Subline_01.SpanSLength_BlockSection(Num_Section * 3 - 2 - 2) + _
                                             (SpanSLength_Half_Adjust - Entity_ICEM_Subline_01.SpanSLength_BlockSection(Num_Section * 3 - 2 - 2)) / 2 * 1.5) / SpanSLength_Half_Adjust * K_Adjust_Tip(nDivide)
                
                ElseIf Span(nSpan) = Num_Section * 3 - 2 Then
                    
                    K_SpanSLength(nDivide) = 1
        
                End If
            
            Next nDivide
            
            
            If nSpan = 1 Then
                                
                Set Spline_Tran_x_Total(nSpan, nIO) = DPH.AddNewJoin(Spline_Root_Part(nIO, 1), Spline_Root_Part(nIO, 2))
                Spline_Tran_x_Total(nSpan, nIO).AddElement Spline_Root_Part(nIO, 3)
                Spline_Tran_x_Total(nSpan, nIO).AddElement Spline_Root_Part(nIO, 4)
 
            ElseIf nSpan > 1 And nSpan < Num_Span Then
                
                Set Spline_Tran_x_Total(nSpan, nIO) = DPH.AddNewSpline
                Spline_Tran_x_Total(nSpan, nIO).SetClosing 1
                    
                For nLine = 1 To 4
                
                    If nLine = 1 Then
                        
                        Set Point_1 = DPH.AddNewPointOnCurveFromPercent(Spline_Tran_y(1, 1, nIO), K_SpanSLength(1), False)
                            
                        Spline_Tran_x_Total(nSpan, nIO).AddPointWithConstraintExplicit Point_1, Nothing, -1#, 1, Nothing, 0#
                        
                    ElseIf nLine = 2 Or nLine = 4 Then
                    
                        For nDivide = 2 To Num_Divide - 1
                        
                            If nLine = 2 Then
                                nDu = 1
                                Index = nDivide
                            Else
                                nDu = 2
                                Index = Num_Divide - nDivide + 1
                            End If
                            
                            Set Point_1 = DPH.AddNewPointOnCurveFromPercent(Spline_Tran_y(nDu, Index, nIO), K_SpanSLength(Index), False)
                            
                            Spline_Tran_x_Total(nSpan, nIO).AddPointWithConstraintExplicit Point_1, Nothing, -1#, 1, Nothing, 0#
                            
                        Next nDivide
                        
                    ElseIf nLine = 3 Then
                        
                        Set Point_1 = DPH.AddNewPointOnCurveFromPercent(Spline_Tran_y(1, Num_Divide, nIO), K_SpanSLength(Num_Divide), False)
                            
                        Spline_Tran_x_Total(nSpan, nIO).AddPointWithConstraintExplicit Point_1, Nothing, -1#, 1, Nothing, 0#
                    
                    End If
                    
                Next nLine
                
                'WorkObject.InsertHybridShape Spline_Tran_x_Total(nSpan, nIO)
            
            ElseIf nSpan = Num_Span Then
            
                Set Spline_Tran_x_Total(nSpan, nIO) = DPH.AddNewJoin(Spline_Tip_Part(nIO, 1), Spline_Tip_Part(nIO, 2))
                Spline_Tran_x_Total(nSpan, nIO).AddElement Spline_Tip_Part(nIO, 3)
                Spline_Tran_x_Total(nSpan, nIO).AddElement Spline_Tip_Part(nIO, 4)
                
                
            End If
                
        Next nIO
    Next nSpan
    
        
    'Create Spline_Tran_x
    For nSpan = 1 To Num_Span
        For nDu = 1 To 2
            For nIO = 1 To 2
                    
                Set Spline_Tran_x(nSpan, nDu, nIO) = DPH.AddNewHybridSplit(Spline_Tran_x_Total(nSpan, nIO), PLANE_XY, (-1) ^ (nDu + 1))
                
                
                If nSpan <> 1 And nSpan <> Num_Span Then
                
                    Set Spline_Tran_x(nSpan, nDu, nIO) = DPH.AddNewProject(Spline_Tran_x(nSpan, nDu, nIO), Surface_ForProject(nIO))
                    Spline_Tran_x(nSpan, nDu, nIO).Normal = True
                    
                End If
                    
                'WorkObject.InsertHybridShape Spline_Tran_x(nSpan, nDU, nIO)
    
            Next nIO
        Next nDu
    Next nSpan
    
    
    '-----------------------------------
    'Create Spline_Tran_z_Point
    '-----------------------------------
    Dim Spline_Tran_z_Point(1 To MaxNum_Array, 1 To 2, 1 To 11, 1 To 2) As Object
    
    For nSpan = 1 To Num_Span
        For nDu = 1 To 2
            For nDivide = 1 To Num_Divide
                For nIO = 1 To 2
                                
                    If Divide(nDivide) = 1 Then
                        K = 0
                    ElseIf Divide(nDivide) = 11 Then
                        K = 1
                    Else
                        If Rate_FrontBack = 1 Then

                            K = (Divide(nDivide) - 1) / 10
                            
                        ElseIf Rate_FrontBack = 2 Then
                        
                            K = Divide(nDivide) / 12
                            
                        End If
                    End If
                
                    If nDu = 1 Then
                        Orientation = False
                    Else
                        Orientation = True
                    End If
                    
                    
                    Set Spline_Tran_z_Point(nSpan, nDu, nDivide, nIO) = DPH.AddNewPointOnCurveFromPercent(Spline_Tran_x(nSpan, nDu, nIO), K, Orientation)
                    
                Next nIO
            Next nDivide
        Next nDu
    Next nSpan
    
    
    '-----------------------------------
    'Change Spline_Tran_y
    '-----------------------------------
    For nDu = 1 To 2
        For nDivide = 1 To Num_Divide
            For nIO = 1 To 2

                Set Spline_Tran_y(nDu, nDivide, nIO) = DPH.AddNewSpline
                
                For nSpan = 1 To Num_Span
                                                         
                    If nSpan = 1 Then
                    
                        Spline_Tran_y(nDu, nDivide, nIO).AddPointWithConstraintFromCurve Spline_Tran_z_Point(nSpan, nDu, nDivide, nIO), Direction_Y, 0.5, 1, 1

                    Else
                    
                        Spline_Tran_y(nDu, nDivide, nIO).AddPointWithConstraintExplicit Spline_Tran_z_Point(nSpan, nDu, nDivide, nIO), Nothing, -1#, 1, Nothing, 0#
                        
                    End If
                    
                Next nSpan
                
                
                'Project
                Set Spline_Tran_y(nDu, nDivide, nIO) = DPH.AddNewProject(Spline_Tran_y(nDu, nDivide, nIO), Surface_ForProject(nIO))
                Spline_Tran_y(nDu, nDivide, nIO).Normal = True
                
            Next nIO
        Next nDivide
    Next nDu


    '-----------------------------------
    'Create Spline_Tran_z
    '-----------------------------------
    Dim Spline_Tran_z(1 To MaxNum_Array, 1 To 2, 1 To 11) As Object

    For nSpan = 1 To Num_Span
        For nDu = 1 To 2
            For nDivide = 1 To Num_Divide

                Set Point_1 = Spline_Tran_z_Point(nSpan, nDu, nDivide, 1)
                Set Point_2 = Spline_Tran_z_Point(nSpan, nDu, nDivide, 2)

                Set Spline_Tran_z(nSpan, nDu, nDivide) = DPH.AddNewLinePtPt(Point_1, Point_2)


                If nSpan = 1 Then

                    Set Spline_Tran_z(nSpan, nDu, nDivide) = DPH.AddNewProject(Spline_Tran_z(nSpan, nDu, nDivide), PLANE_ZX)
                    Spline_Tran_z(nSpan, nDu, nDivide).Normal = False
                    Spline_Tran_z(nSpan, nDu, nDivide).Direction = Direction_Y

                End If

            Next nDivide
        Next nDu

    Next nSpan

    
    '-----------------------------------
    'Create Spline_Tran_Tip_x
    '-----------------------------------
    Dim Spline_Tran_Tip_x(1 To 2) As Object

    For nIO = 1 To 2

        Set Point_1 = Spline_Tran_z_Point(Num_Span, 1, 1, nIO)
        Set Point_2 = Spline_Tran_z_Point(Num_Span, 1, Num_Divide, nIO)

        Set Spline_Tran_Tip_x(nIO) = DPH.AddNewLinePtPt(Point_1, Point_2)


        Set Spline_Tran_Tip_x(nIO) = DPH.AddNewProject(Spline_Tran_Tip_x(nIO), Surface_ForProject(nIO))
        Spline_Tran_Tip_x(nIO).Normal = True

        'WorkObject.InsertHybridShape Spline_Tran_Tip_x(nIO)

    Next nIO
    
    
    '-----------------------------------
    'Create Spline_Tran_Tip_Point
    '-----------------------------------
    Dim Spline_Tran_Tip_Point(1 To 11, 1 To 2) As Object

    For nTip = 1 To Num_Divide - 4
        For nIO = 1 To 2
            
            Set Spline_Tran_Tip_Point(nTip, nIO) = DPH.AddNewPointOnCurveFromPercent(Spline_Tran_Tip_x(nIO), nTip / (Num_Divide - 3), False)
            
            'WorkObject.InsertHybridShape Spline_Tran_Tip_Point(nTip, nIO)

        Next nIO
    Next nTip
    
    
    '-----------------------------------
    'Create Spline_Tran_Tip_y
    '-----------------------------------
    Dim Spline_Tran_Tip_y(1 To 11, 1 To 2) As Object
    
    For nTip = 1 To Num_Divide - 4
        For nIO = 1 To 2
            
            nDivide = nTip + 2
            
            Set Point_1 = Spline_Tran_z_Point(Num_Span, 1, nDivide, nIO)
            Set Point_2 = Spline_Tran_z_Point(Num_Span, 2, nDivide, nIO)
            
            Set Spline_1 = Spline_Tran_y(1, nDivide, nIO)
            Set Spline_2 = Spline_Tran_y(2, nDivide, nIO)
  
  
            Set Spline_Tran_Tip_y(nTip, nIO) = DPH.AddNewSpline
            
            Spline_Tran_Tip_y(nTip, nIO).AddPointWithConstraintFromCurve Point_1, Spline_1, 0.7, 1, 1
            
            Spline_Tran_Tip_y(nTip, nIO).AddPointWithConstraintExplicit Spline_Tran_Tip_Point(nTip, nIO), Nothing, -1#, 1, Nothing, 0#
            
            Spline_Tran_Tip_y(nTip, nIO).AddPointWithConstraintFromCurve Point_2, Spline_2, 0.7, -1, 1
    
    
            Set Spline_Tran_Tip_y(nTip, nIO) = DPH.AddNewProject(Spline_Tran_Tip_y(nTip, nIO), Surface_ForProject(nIO))
    
            Spline_Tran_Tip_y(nTip, nIO).Normal = True
    
            'WorkObject.InsertHybridShape Spline_Tran_Tip_y(nTip, nIO)

        Next nIO
    Next nTip


    '-----------------------------------
    'Create Spline_Tran_Tip_z
    '-----------------------------------
    Dim Spline_Tran_Tip_z(1 To 11) As Object
    
    For nTip = 1 To Num_Divide - 4
        
        Set Point_1 = Spline_Tran_Tip_Point(nTip, 1)
        Set Point_2 = Spline_Tran_Tip_Point(nTip, 2)
    
        Set Spline_Tran_Tip_z(nTip) = DPH.AddNewLinePtPt(Point_1, Point_2)
    
    Next nTip
    
    
    '-----------------------------------
    'Smooth
    '-----------------------------------
    'Spline_Tran_x
    For nSpan = 1 To Num_Span
        For nDu = 1 To 2
            For nIO = 1 To 2
    
                Set Spline_Tran_x(nSpan, nDu, nIO) = DPH.AddNewCurveSmooth(Spline_Tran_x(nSpan, nDu, nIO))
                Spline_Tran_x(nSpan, nDu, nIO).SetMaximumDeviation 0.001
                Spline_Tran_x(nSpan, nDu, nIO).CorrectionMode = 3
    
            Next nIO
        Next nDu
    Next nSpan
        
        
    '-----------------------------------
    'Extract
    '-----------------------------------
    'Spline_Tran_z_Point
    Set Extract_Spline_Tran_z_Point = DPH.AddNewExtractMulti(EmptyObject)
    Set Extract_Spline_Tran_z_Point_Repeat = DPH.AddNewExtractMulti(EmptyObject)

    For nSpan = 1 To Num_Span
        For nDu = 1 To 2
            For nDivide = 1 To Num_Divide
                For nIO = 1 To 2
                                        
                    nSection = Int(Span(nSpan) / 3) + 1
                    
                    If Not IsInArray(nSection, Index_NonActSection_ICEM) Then
                    
                        If Not ((nDu = 2 And nDivide = 1) Or (nDu = 2 And nDivide = Num_Divide)) Then
        
                            Extract_Spline_Tran_z_Point.AddConstraintTolerant Spline_Tran_z_Point(nSpan, nDu, nDivide, nIO), 3, False, False, 0.1, 0.5, 0.98, 1
                            Extract_Spline_Tran_z_Point.SetElement 1, Spline_Tran_z_Point(nSpan, nDu, nDivide, nIO)
                        
                        Else
                            
                            Extract_Spline_Tran_z_Point_Repeat.AddConstraintTolerant Spline_Tran_z_Point(nSpan, nDu, nDivide, nIO), 3, False, False, 0.1, 0.5, 0.98, 1
                            Extract_Spline_Tran_z_Point_Repeat.SetElement 1, Spline_Tran_z_Point(nSpan, nDu, nDivide, nIO)
                            
                        End If
                    
                    End If
                
                Next nIO
            Next nDivide
        Next nDu
    Next nSpan

    WorkObject.InsertHybridShape Extract_Spline_Tran_z_Point
    WorkObject.InsertHybridShape Extract_Spline_Tran_z_Point_Repeat
    
    Extract_Spline_Tran_z_Point.Name = "Spline_Tran_z_Point"
    Extract_Spline_Tran_z_Point_Repeat.Name = "Spline_Tran_z_Point_Repeat"
    

    'Spline_Tran_Tip_Point
    Set Extract_Spline_Tran_Tip_Point = DPH.AddNewExtractMulti(EmptyObject)

    For nTip = 1 To Num_Divide - 4
        For nIO = 1 To 2

            Extract_Spline_Tran_Tip_Point.AddConstraintTolerant Spline_Tran_Tip_Point(nTip, nIO), 3, False, False, 0.1, 0.5, 0.98, 1
            Extract_Spline_Tran_Tip_Point.SetElement 1, Spline_Tran_Tip_Point(nTip, nIO)
                
        Next nIO
    Next nTip

    WorkObject.InsertHybridShape Extract_Spline_Tran_Tip_Point

    Extract_Spline_Tran_Tip_Point.Name = "Spline_Tran_Tip_Point"
    
    
    'Spline_Tran_x
    Set Extract_Spline_Tran_x = DPH.AddNewExtractMulti(EmptyObject)

    For nSpan = 1 To Num_Span
        For nDu = 1 To 2
            For nIO = 1 To 2
                
                nSection = Int(Span(nSpan) / 3) + 1
                    
                If Not IsInArray(nSection, Index_NonActSection_ICEM) Then
                
                    Extract_Spline_Tran_x.AddConstraintTolerant Spline_Tran_x(nSpan, nDu, nIO), 3, False, False, 0.1, 0.5, 0.98, 1
                    Extract_Spline_Tran_x.SetElement 1, Spline_Tran_x(nSpan, nDu, nIO)
                
                End If
                    
            Next nIO
        Next nDu
    Next nSpan

    WorkObject.InsertHybridShape Extract_Spline_Tran_x
    
    Extract_Spline_Tran_x.Name = "Spline_Tran_x"
    
    
    'Spline_Tran_y
    Set Extract_Spline_Tran_y = DPH.AddNewExtractMulti(EmptyObject)
    
    For nDu = 1 To 2
        For nDivide = 1 To Num_Divide
            For nIO = 1 To 2

                If Not ((nDu = 2 And nDivide = 1) Or (nDu = 2 And nDivide = Num_Divide)) Then
                
                    Extract_Spline_Tran_y.AddConstraintTolerant Spline_Tran_y(nDu, nDivide, nIO), 3, False, False, 0.1, 0.5, 0.98, 1
                    Extract_Spline_Tran_y.SetElement 1, Spline_Tran_y(nDu, nDivide, nIO)
                    
                End If
                
            Next nIO
       Next nDivide
    Next nDu

    WorkObject.InsertHybridShape Extract_Spline_Tran_y
    
    Extract_Spline_Tran_y.Name = "Spline_Tran_y"
    
    
    'Spline_Tran_z
    Set Extract_Spline_Tran_z = DPH.AddNewExtractMulti(EmptyObject)

    For nSpan = 1 To Num_Span
        For nDu = 1 To 2
            For nDivide = 1 To Num_Divide
                
                nSection = Int(Span(nSpan) / 3) + 1
                    
                If Not IsInArray(nSection, Index_NonActSection_ICEM) Then
                
                    If Not ((nDu = 2 And nDivide = 1) Or (nDu = 2 And nDivide = Num_Divide)) Then
                    
                        Extract_Spline_Tran_z.AddConstraintTolerant Spline_Tran_z(nSpan, nDu, nDivide), 3, False, False, 0.1, 0.5, 0.98, 1
                        Extract_Spline_Tran_z.SetElement 1, Spline_Tran_z(nSpan, nDu, nDivide)
                        
                    End If
                
                End If
                    
            Next nDivide
        Next nDu
    Next nSpan

    WorkObject.InsertHybridShape Extract_Spline_Tran_z
    
    Extract_Spline_Tran_z.Name = "Spline_Tran_z"
    

    'Spline_Tran_Tip_xyz
    Set Extract_Spline_Tran_Tip_xyz = DPH.AddNewExtractMulti(EmptyObject)
    
    For nTip = 1 To Num_Divide - 4
        For nIO = 1 To 2
                
            Extract_Spline_Tran_Tip_xyz.AddConstraintTolerant Spline_Tran_Tip_y(nTip, nIO), 3, False, False, 0.1, 0.5, 0.98, 1
            Extract_Spline_Tran_Tip_xyz.SetElement 1, Spline_Tran_Tip_y(nTip, nIO)
    
        Next nIO
    Next nTip
    
    For nIO = 1 To 2
                    
        Extract_Spline_Tran_Tip_xyz.AddConstraintTolerant Spline_Tran_Tip_x(nIO), 3, False, False, 0.1, 0.5, 0.98, 1
        Extract_Spline_Tran_Tip_xyz.SetElement 1, Spline_Tran_Tip_x(nIO)
    
    Next nIO

    For nTip = 1 To Num_Divide - 4
    
        Extract_Spline_Tran_Tip_xyz.AddConstraintTolerant Spline_Tran_Tip_z(nTip), 3, False, False, 0.1, 0.5, 0.98, 1
        Extract_Spline_Tran_Tip_xyz.SetElement 1, Spline_Tran_Tip_z(nTip)
        
    Next nTip

    WorkObject.InsertHybridShape Extract_Spline_Tran_Tip_xyz

    Extract_Spline_Tran_Tip_xyz.Name = "Spline_Tran_Tip_xyz"
    
    
    'Hide
    DocumentObject.Selection.Add Extract_Spline_Tran_z_Point_Repeat
    
    DocumentObject.Selection.VisProperties.SetShow 1
    DocumentObject.Selection.Clear
    
    
    '-----------------------------------
    'Return
    '-----------------------------------
    ReDim ICEM_Subline_23.Divide(1 To Num_Divide)
    For nDivide = 1 To Num_Divide
        ICEM_Subline_23.Divide(nDivide) = Divide(nDivide)
    Next nDivide
    
    ICEM_Subline_23.Num_Divide = Num_Divide
    
    
    ReDim ICEM_Subline_23.Span(1 To Num_Span)
    For nSpan = 1 To Num_Span
        ICEM_Subline_23.Span(nSpan) = Span(nSpan)
    Next nSpan
    
    ICEM_Subline_23.Num_Span = Num_Span

    
    ReDim ICEM_Subline_23.Spline_Tran_z_Point(1 To Num_Span, 1 To 2, 1 To Num_Divide, 1 To 2)
    For nSpan = 1 To Num_Span
        For nDu = 1 To 2
            For nDivide = 1 To Num_Divide
                For nIO = 1 To 2

                    Set ICEM_Subline_23.Spline_Tran_z_Point(nSpan, nDu, nDivide, nIO) = Spline_Tran_z_Point(nSpan, nDu, nDivide, nIO)
                
                Next nIO
            Next nDivide
        Next nDu
    Next nSpan

    
    ReDim ICEM_Subline_23.Spline_Tran_Tip_Point(1 To Num_Divide - 4, 1 To 2)
    For nTip = 1 To Num_Divide - 4
        For nIO = 1 To 2

            Set ICEM_Subline_23.Spline_Tran_Tip_Point(nTip, nIO) = Spline_Tran_Tip_Point(nTip, nIO)

        Next nIO
    Next nTip
    
    
    ReDim ICEM_Subline_23.Spline_Tran_x(1 To Num_Span, 1 To 2, 1 To 2)
    For nSpan = 1 To Num_Span
        For nDu = 1 To 2
            For nIO = 1 To 2
    
                Set ICEM_Subline_23.Spline_Tran_x(nSpan, nDu, nIO) = Spline_Tran_x(nSpan, nDu, nIO)
                       
            Next nIO
        Next nDu
    Next nSpan


    ReDim ICEM_Subline_23.Spline_Tran_y(1 To 2, 1 To Num_Divide, 1 To 2)
    For nDu = 1 To 2
        For nDivide = 1 To Num_Divide
            For nIO = 1 To 2
                
                Set ICEM_Subline_23.Spline_Tran_y(nDu, nDivide, nIO) = Spline_Tran_y(nDu, nDivide, nIO)

            Next nIO
       Next nDivide
    Next nDu
    
    
    ReDim ICEM_Subline_23.Spline_Tran_z(1 To Num_Span, 1 To 2, 1 To Num_Divide)
    For nSpan = 1 To Num_Span
        For nDu = 1 To 2
            For nDivide = 1 To Num_Divide

                Set ICEM_Subline_23.Spline_Tran_z(nSpan, nDu, nDivide) = Spline_Tran_z(nSpan, nDu, nDivide)
                    
            Next nDivide
        Next nDu
    Next nSpan
    
    
    ReDim ICEM_Subline_23.Spline_Tip_Part(1 To 2, 1 To 4)
    For nIO = 1 To 2
        For nLine = 1 To 4

            Set ICEM_Subline_23.Spline_Tip_Part(nIO, nLine) = Spline_Tip_Part(nIO, nLine)

        Next nLine
    Next nIO
    
    
    ReDim ICEM_Subline_23.Spline_Tran_Tip_x(1 To 2)
    For nIO = 1 To 2
    
        Set ICEM_Subline_23.Spline_Tran_Tip_x(nIO) = Spline_Tran_Tip_x(nIO)
    
    Next nIO
    
    
    ReDim ICEM_Subline_23.Spline_Tran_Tip_y(1 To Num_Divide - 4, 1 To 2)
    For nTip = 1 To Num_Divide - 4
        For nIO = 1 To 2
    
            Set ICEM_Subline_23.Spline_Tran_Tip_y(nTip, nIO) = Spline_Tran_Tip_y(nTip, nIO)
    
        Next nIO
    Next nTip
    
    
    ReDim ICEM_Subline_23.Spline_Tran_Tip_z(1 To Num_Divide - 4)
    For nTip = 1 To Num_Divide - 4
    
        Set ICEM_Subline_23.Spline_Tran_Tip_z(nTip) = Spline_Tran_Tip_z(nTip)
    
    Next nTip
    
        
    Set ICEM_Subline_23.Extract_Spline_Tran_z_Point = Extract_Spline_Tran_z_Point
    Set ICEM_Subline_23.Extract_Spline_Tran_Tip_Point = Extract_Spline_Tran_Tip_Point
    Set ICEM_Subline_23.Extract_Spline_Tran_x = Extract_Spline_Tran_x
    Set ICEM_Subline_23.Extract_Spline_Tran_y = Extract_Spline_Tran_y
    Set ICEM_Subline_23.Extract_Spline_Tran_z = Extract_Spline_Tran_z
    Set ICEM_Subline_23.Extract_Spline_Tran_Tip_xyz = Extract_Spline_Tran_Tip_xyz
    
End Function


'*****************************
'ICEM_Subline_12
'*****************************
Function ICEM_Subline_12(ByVal DocumentObject As Object, _
                         ByRef Entity_ICEM_FluidAndBOI As Type_ICEM_FluidAndBOI, _
                         ByRef Entity_ICEM_Subline_01 As Type_ICEM_Subline_01, _
                         ByRef Entity_ICEM_Subline_23 As Type_ICEM_Subline_23, _
                         ByVal Data_SectionPoint As Variant, ByVal Num_Section As Integer, ByVal Num_PointPerSpline As Integer, _
                         ByVal MAC_Length As Double, ByVal MAC_x As Double, _
                         ByVal Diameter_Fillet As Double, ByVal Rate_Fluid As Double, ByVal Rate_BOI_Fluid_MAC As Double, ByVal Rate_BOI_Fluid_Span As Double, _
                         ByVal Index_NonActSection_ICEM As Variant, ByVal Index_Layer2Connect_ICEM As Variant) _
                         As Type_ICEM_Subline_12

    'CreateOrderGeometry
    Set WorkObject = DocumentObject.Part.OrderedGeometricalSets.Add()
    DocumentObject.Part.OrderedGeometricalSets.Item(7).Name = "ICEM_Subline_12"
    
    
    Set DPH = DocumentObject.Part.HybridShapeFactory
    
    Num_Spline = Num_Section * 2
    
    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Define
    '-----------------------------------
    Rate_FrontBack = 1
    
    
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
        
        
    'Length_Chord_BlockSection
    Dim Length_Chord_BlockSection(1 To MaxNum_Array) As Double
    
    For nSpan = 1 To Num_Section * 3 - 2
        
        Length_Chord_BlockSection(nSpan) = Entity_ICEM_Subline_01.Length_Chord_BlockSection(nSpan)
        
    Next nSpan
    
    
    'Length_Chord_BlockSection_2
    Dim Length_Chord_BlockSection_2(1 To MaxNum_Array) As Double
    
    Span_Half = Data_SectionPoint(Num_Section * Num_PointPerSpline, 2) - Data_SectionPoint(Num_PointPerSpline, 2)
        
    SweepbackAngle_Trail = Atn((Data_SectionPoint(Num_Section * Num_PointPerSpline, 1) - Data_SectionPoint(Num_PointPerSpline, 1)) / Span_Half) * 57.3
    
    
    If SweepbackAngle_Trail > 0 Then
    
        Length_Ref_Root = Span_Half * Tan(SweepbackAngle_Trail / 3 / 57.3) + 0.4 * MAC_Length
    
    Else
    
        Length_Ref_Root = 0.4 * MAC_Length
    
    End If
    
    If Length_Chord(Num_Section) < 0.4 * MAC_Length Then
        Length_Ref_Tip = (0.4 * MAC_Length + Length_Chord(Num_Section)) / 2
    Else
        Length_Ref_Tip = 0.4 * MAC_Length
    End If
    
    
    For nSpan = 1 To Num_Section * 3 - 2
    
        Length_Chord_BlockSection_2(nSpan) = Length_Ref_Root + Entity_ICEM_Subline_01.Span_BlockSection(nSpan) / Entity_ICEM_Subline_01.Span_BlockSection(Num_Section * 3 - 2) * (Length_Ref_Tip - Length_Ref_Root)
        
    Next nSpan
    

    'Point_Ref
    Dim Point_Ref(1 To 3, 1 To 2) As Object
    
    X1 = Length_Chord(1) / 2
    Y1 = 0
    Z1 = 0
    
    Set Point_Ref(1, 1) = DPH.AddNewPointCoord(X1, Y1, Z1)
    
    X1 = Length_Chord(1) / 2 - Entity_ICEM_FluidAndBOI.Radius_BOI_Fluid_BasedMAC
    Y1 = 0
    Z1 = 0
    
    Set Point_Ref(2, 1) = DPH.AddNewPointCoord(X1, Y1, Z1)

    X1 = Length_Chord(1) / 2
    Y1 = 0
    Z1 = Entity_ICEM_FluidAndBOI.Radius_BOI_Fluid_BasedMAC
    
    Set Point_Ref(3, 1) = DPH.AddNewPointCoord(X1, Y1, Z1)
    
    
    X1 = Length_Chord(1) / 2
    Y1 = 0
    Z1 = 0
    
    Set Point_Ref(1, 2) = DPH.AddNewPointCoord(X1, Y1, Z1)
    
    X1 = Length_Chord(1) / 2 - Entity_ICEM_FluidAndBOI.Radius_Fluid
    Y1 = 0
    Z1 = 0
    
    Set Point_Ref(2, 2) = DPH.AddNewPointCoord(X1, Y1, Z1)

    X1 = Length_Chord(1) / 2
    Y1 = 0
    Z1 = Entity_ICEM_FluidAndBOI.Radius_Fluid
    
    Set Point_Ref(3, 2) = DPH.AddNewPointCoord(X1, Y1, Z1)
    
    
    'Surface_ForProject
    Set Surface_ForProject = Entity_ICEM_FluidAndBOI.Surface_BOI_Fluid
    
    
    'Divide
    Divide = Entity_ICEM_Subline_23.Divide
    Num_Divide = Entity_ICEM_Subline_23.Num_Divide
    
    Divide_Sub = Array(999, 1, 2, 6, 10, 11)
    Num_Divide_Sub = UBound(Divide_Sub) - LBound(Divide_Sub)
    
    
    'Span
    Span = Entity_ICEM_Subline_23.Span
    Num_Span = Entity_ICEM_Subline_23.Num_Span
    
    
    'Layer
    Dim Layer(1 To MaxNum_Array, 1 To 10) As Double
    
    Num_Layer = 6

    For nSpan = 1 To Num_Span
        For nLayer = 2 To Num_Layer
            
            x0 = (nLayer - 2) / (Num_Layer - 2)
            
            y0 = 1 - Cos(x0 * Pi / 2)

            Layer(nSpan, nLayer) = y0

        Next nLayer
    Next nSpan
    
    
    '-----------------------------------
    'Create Spline_Tran_z_Sub
    '-----------------------------------
    Dim Spline_Tran_z_Sub(1 To MaxNum_Array, 1 To 2, 1 To 11) As Object

    For nSpan = 1 To Num_Span
        For nDu = 1 To 2
            For nDivide_Sub = 1 To Num_Divide_Sub
                
                Set Point_1 = Entity_ICEM_Subline_01.Spline_SectionOffset_Point(Span(nSpan), nDu, Divide_Sub(nDivide_Sub), 2)
                Set Spline_1 = Entity_ICEM_Subline_01.Line_NormalVector(Span(nSpan), nDu, Divide_Sub(nDivide_Sub))
                
                Set Point_2 = Entity_ICEM_Subline_23.Spline_Tran_z_Point(nSpan, nDu, Divide_Sub(nDivide_Sub), 1)
                Set Spline_2 = Entity_ICEM_Subline_23.Spline_Tran_z(nSpan, nDu, Divide_Sub(nDivide_Sub))
                
                
                If Rate_FrontBack = 1 Then
                
                    If nSpan = Num_Span And Divide_Sub(nDivide_Sub) = 6 Then
                    
                        Dihedral_1 = Entity_ICEM_Subline_01.Dihedral(Num_Section * 3 - 2)
                        
                        If nDu = 1 And Dihedral_1 < 0 Then
                        
                            K_1 = 0.1 + Abs(Dihedral_1) / 2 * 0.01
                        
                        ElseIf nDu = 2 And Dihedral_1 > 0 Then
                        
                            K_1 = 0.1 + Abs(Dihedral_1) / 2 * 0.01
                        
                        Else
                        
                            K_1 = 0.1
                        
                        End If
                        
                        If K_1 >= 0.2 Then
                            K_1 = 0.2
                        End If
  
                    Else
                    
                        K_1 = 0.2
                        
                    End If
                    
                ElseIf Rate_FrontBack = 2 Then
                
                    K_1 = 0.2
                    
                End If
                
                K_2 = 1

                Set Spline_Tran_z_Sub(nSpan, nDu, nDivide_Sub) = DPH.AddNewSpline
                Spline_Tran_z_Sub(nSpan, nDu, nDivide_Sub).AddPointWithConstraintFromCurve Point_1, Spline_1, K_1, 1, 1
                Spline_Tran_z_Sub(nSpan, nDu, nDivide_Sub).AddPointWithConstraintFromCurve Point_2, Spline_2, K_2, 1, 1


                If nSpan = 1 Then

                    Set Spline_Tran_z_Sub(nSpan, nDu, nDivide_Sub) = DPH.AddNewProject(Spline_Tran_z_Sub(nSpan, nDu, nDivide_Sub), PLANE_ZX)
                    Spline_Tran_z_Sub(nSpan, nDu, nDivide_Sub).Normal = False
                    Spline_Tran_z_Sub(nSpan, nDu, nDivide_Sub).Direction = Direction_Y
                    
                End If
                
               'WorkObject.InsertHybridShape Spline_Tran_z_Sub(nSpan, nDU, nDivide_Sub)
                
            Next nDivide_Sub
        Next nDu

    Next nSpan
    
    
    '-----------------------------------
    'Create Spline_Tran_x
    '-----------------------------------
    Dim Length_Offset_Layer_2(1 To MaxNum_Array) As Double
    
    Dim Spline_Tran_z_Sub_Point(1 To MaxNum_Array, 1 To 2, 1 To 11, 1 To 10) As Object
    Dim Spline_Tran_z_Sub_Outer(1 To MaxNum_Array, 1 To 2, 1 To 11) As Object
       
    Dim Spline_Tran_x_Total(1 To MaxNum_Array, 1 To 10) As Object
    Dim Spline_Tran_x(1 To MaxNum_Array, 1 To 2, 1 To 10) As Object


    'Create Spline_Tran_z_Sub_Point
    For nSpan = 1 To Num_Span
        For nLayer = 1 To Num_Layer
            
            If nLayer = 1 Then
                
                For nDu = 1 To 2
                    For nDivide_Sub = 1 To Num_Divide_Sub
                        
                        Set Spline_Tran_z_Sub_Point(nSpan, nDu, nDivide_Sub, nLayer) = Entity_ICEM_Subline_01.Spline_SectionOffset_Point(Span(nSpan), nDu, Divide_Sub(nDivide_Sub), 2)
                    
                    Next nDivide_Sub
                Next nDu

            ElseIf nLayer > 1 And nLayer < Num_Layer Then
            
                If nLayer = 2 Then
                                                            
                    For nDu = 1 To 2
                        For nDivide_Sub = 1 To Num_Divide_Sub

                            Length_Offset_Layer_2(nSpan) = Length_Chord_BlockSection(Span(nSpan)) * 1.5
                            
                            Set Spline_Tran_z_Sub_Point(nSpan, nDu, nDivide_Sub, nLayer) = DPH.AddNewPointOnCurveFromDistance(Spline_Tran_z_Sub(nSpan, nDu, nDivide_Sub), Length_Offset_Layer_2(nSpan), False)
                    
                        Next nDivide_Sub
                    Next nDu
                    
                Else
                    
                    For nDu = 1 To 2
                        For nDivide_Sub = 1 To Num_Divide_Sub

                            Set Spline_Tran_z_Sub_Outer(nSpan, nDu, nDivide_Sub) = DPH.AddNewHybridSplit(Spline_Tran_z_Sub(nSpan, nDu, nDivide_Sub), Spline_Tran_z_Sub_Point(nSpan, nDu, nDivide_Sub, 2), -1)
                            
                            Set Spline_Tran_z_Sub_Point(nSpan, nDu, nDivide_Sub, nLayer) = DPH.AddNewPointOnCurveFromPercent(Spline_Tran_z_Sub_Outer(nSpan, nDu, nDivide_Sub), Layer(nSpan, nLayer), False)
                        
                        Next nDivide_Sub
                    Next nDu
                    
                End If
                
            ElseIf nLayer = Num_Layer Then
                
                For nDu = 1 To 2
                    For nDivide_Sub = 1 To Num_Divide_Sub
                    
                        Set Spline_Tran_z_Sub_Point(nSpan, nDu, nDivide_Sub, nLayer) = Entity_ICEM_Subline_23.Spline_Tran_z_Point(nSpan, nDu, Divide_Sub(nDivide_Sub), 1)
                    
                    Next nDivide_Sub
                Next nDu
                
            End If
            
        Next nLayer
    Next nSpan
    
    
    'Create Spline_Tran_x_Total
    For nSpan = 1 To Num_Span
        For nLayer = 1 To Num_Layer
            
            If nLayer = 1 Then
                
                Set Spline_1 = Entity_ICEM_Subline_01.Spline_SectionOffset(Span(nSpan), 1)
                Set Spline_2 = Entity_ICEM_Subline_01.Spline_SectionOffset(Span(nSpan), 2)

                Set Spline_Tran_x_Total(nSpan, nLayer) = DPH.AddNewJoin(Spline_1, Spline_2)
            
            ElseIf nLayer > 1 And nLayer < Num_Layer Then
 
                Set Spline_Tran_x_Total(nSpan, nLayer) = DPH.AddNewSpline
                Spline_Tran_x_Total(nSpan, nLayer).SetClosing 1
                    
                For nDu = 1 To 2
                    For nDivide_Sub = 1 To Num_Divide_Sub - 1
                         
                        If nDu = 1 Then
                            Index = nDivide_Sub
                        Else
                            Index = Num_Divide_Sub - nDivide_Sub + 1
                        End If
                        
                        If nLayer = 2 And nSpan < Num_Span - 1 Then
                            
                            If Divide_Sub(nDivide_Sub) <> 2 And Divide_Sub(nDivide_Sub) <> 10 Then
                            
                                Spline_Tran_x_Total(nSpan, nLayer).AddPointWithConstraintExplicit Spline_Tran_z_Sub_Point(nSpan, nDu, Index, nLayer), Nothing, -1#, 1, Nothing, 0#
                                
                            End If
                            
                        Else
                            
                            Spline_Tran_x_Total(nSpan, nLayer).AddPointWithConstraintExplicit Spline_Tran_z_Sub_Point(nSpan, nDu, Index, nLayer), Nothing, -1#, 1, Nothing, 0#
                            
                        End If
                            
                    Next nDivide_Sub
                Next nDu
                
            ElseIf nLayer = Num_Layer Then
                
                Set Spline_1 = Entity_ICEM_Subline_23.Spline_Tran_x(nSpan, 1, 1)
                Set Spline_2 = Entity_ICEM_Subline_23.Spline_Tran_x(nSpan, 2, 1)

                Set Spline_Tran_x_Total(nSpan, nLayer) = DPH.AddNewJoin(Spline_1, Spline_2)
            
            End If
            
            
            If nSpan = 1 Then

                Set Spline_Tran_x_Total(nSpan, nLayer) = DPH.AddNewProject(Spline_Tran_x_Total(nSpan, nLayer), PLANE_ZX)
                Spline_Tran_x_Total(nSpan, nLayer).Normal = False
                Spline_Tran_x_Total(nSpan, nLayer).Direction = Direction_Y
                
            End If
            
            'WorkObject.InsertHybridShape Spline_Tran_x_Total(nSpan, nLayer)

        Next nLayer
    Next nSpan
    
    
    'Create Spline_Tran_x
    For nSpan = 1 To Num_Span
        For nLayer = 1 To Num_Layer
            For nDu = 1 To 2
                
                If nLayer = 1 Then
                    
                    Set Spline_Tran_x(nSpan, nDu, nLayer) = Entity_ICEM_Subline_01.Spline_SectionOffset(Span(nSpan), nDu)
                    
                Else
                    
                    If nDu = 1 Then
                    
                        Set Point_1 = Spline_Tran_z_Sub_Point(nSpan, nDu, 1, nLayer)
                        Set Point_2 = Spline_Tran_z_Sub_Point(nSpan, nDu, Num_Divide_Sub, nLayer)
                        
                        
                        Set Line_ToSplit = DPH.AddNewLinePtPt(Point_1, Point_2)
                                        
                        Set Line_ToSplit = DPH.AddNewExtrapolLength(Point_1, Line_ToSplit, MAC_Length)
                        Line_ToSplit.BorderType = 1
                        Line_ToSplit.SetAssemble True
                        Line_ToSplit.SetContinuityType 1, 1
                        
                        Set Line_ToSplit = DPH.AddNewExtrapolLength(Point_2, Line_ToSplit, MAC_Length)
                        Line_ToSplit.BorderType = 1
                        Line_ToSplit.SetAssemble True
                        Line_ToSplit.SetContinuityType 1, 1
                        
                        
                        Set Surface_ToSplit = DPH.AddNewExtrude(Line_ToSplit, MAC_Length, MAC_Length, Direction_Y)
                    
                    End If
                    
                     
                    Set Spline_Tran_x(nSpan, nDu, nLayer) = DPH.AddNewHybridSplit(Spline_Tran_x_Total(nSpan, nLayer), Surface_ToSplit, (-1) ^ (nDu + 1))
    
                End If
                
            Next nDu
        Next nLayer
    Next nSpan
    
    
    '-----------------------------------
    'Create Spline_Tran_z_Point
    '-----------------------------------
    Dim Spline_Tran_z_Point(1 To MaxNum_Array, 1 To 2, 1 To 11, 1 To 10) As Object
    
    
    For nSpan = 1 To Num_Span
        For nDu = 1 To 2
            For nDivide = 1 To Num_Divide
                For nLayer = 1 To Num_Layer
                     
                    If nLayer = 1 Then
                    
                        Set Spline_Tran_z_Point(nSpan, nDu, nDivide, nLayer) = Entity_ICEM_Subline_01.Spline_SectionOffset_Point(Span(nSpan), nDu, Divide(nDivide), 2)
                        
                    ElseIf nLayer > 1 And nLayer < Num_Layer Then
                        
                        If Divide(nDivide) = 1 Then
                            K = 0
                        ElseIf Divide(nDivide) = 11 Then
                            K = 1
                        Else
                            If Rate_FrontBack = 1 Then
                        
                                K = (Divide(nDivide) - 1) / 10
                            
                            ElseIf Rate_FrontBack = 2 Then
                            
                                K = Divide(nDivide) / 12
                                
                            End If
                        End If
    
                        If nDu = 1 Then
                            Orientation = False
                        Else
                            Orientation = True
                        End If
                        
                        
                        Set Spline_Tran_z_Point(nSpan, nDu, nDivide, nLayer) = DPH.AddNewPointOnCurveFromPercent(Spline_Tran_x(nSpan, nDu, nLayer), K, Orientation)
                
                    ElseIf nLayer = Num_Layer Then
                        
                        Set Spline_Tran_z_Point(nSpan, nDu, nDivide, nLayer) = Entity_ICEM_Subline_23.Spline_Tran_z_Point(nSpan, nDu, nDivide, 1)
                    
                    End If

                Next nLayer
            Next nDivide
        Next nDu
    Next nSpan
    
    
    '-----------------------------------
    'Change Tip
    '-----------------------------------
    Dim Spline_Tip_Point(1 To 10, 1 To 22) As Object
    Dim Spline_Tip_Part(1 To 10, 1 To 4) As Object
    
    
    'Create Spline_Tip_Point
    For nLayer = 2 To Num_Layer - 1
        
        nPoint = 1
        
        For nDu = 1 To 2
            For nDivide = 1 To Num_Divide - 1
  
                If nDu = 1 Then
                    Index = nDivide
                Else
                    Index = Num_Divide - nDivide + 1
                End If
                
                If Index = 1 Or Index = 2 Or Index = (Num_Divide + 1) / 2 Or Index = Num_Divide - 1 Or Index = Num_Divide Then
                
                    nPoint = nPoint + 1
                    
                    Set Spline_Tip_Point(nLayer, nPoint) = Spline_Tran_z_Point(Num_Span, nDu, Index, nLayer)
                    
                End If
    
            Next nDivide
        Next nDu
    
        Set Spline_Tip_Point(nLayer, 1) = Spline_Tip_Point(nLayer, 9)
        
    Next nLayer
          
    
    'Create Spline_Tip_Part
    Index = Array(999, 1, 3, 5, 7)
    
    For nLayer = 2 To Num_Layer - 1
        For nLine = 1 To 4
    
            Set Spline_Tip_Part(nLayer, nLine) = DPH.AddNewSpline
    
            Num = 3
    
            For i = 0 To Num - 1
                Spline_Tip_Part(nLayer, nLine).AddPointWithConstraintExplicit Spline_Tip_Point(nLayer, Index(nLine) + i), Nothing, -1#, 1, Nothing, 0#
            Next i
                
        Next nLine
    Next nLayer
    
    
    'Change Spline_Tran_x_Total
    For nLayer = 2 To Num_Layer - 1
    
        Set Spline_Tran_x_Total(Num_Span, nLayer) = DPH.AddNewJoin(Spline_Tip_Part(nLayer, 1), Spline_Tip_Part(nLayer, 2))
        Spline_Tran_x_Total(Num_Span, nLayer).AddElement Spline_Tip_Part(nLayer, 3)
        Spline_Tran_x_Total(Num_Span, nLayer).AddElement Spline_Tip_Part(nLayer, 4)
        
    Next nLayer
    
    
    'Change Spline_Tran_x
    For nLayer = 2 To Num_Layer - 1
        For nDu = 1 To 2
                
            If nDu = 1 Then
            
                Set Point_1 = Spline_Tip_Point(nLayer, 2)
                Set Point_2 = Spline_Tip_Point(nLayer, 6)
                
                
                Set Line_ToSplit = DPH.AddNewLinePtPt(Point_1, Point_2)
                                
                Set Line_ToSplit = DPH.AddNewExtrapolLength(Point_1, Line_ToSplit, MAC_Length)
                Line_ToSplit.BorderType = 1
                Line_ToSplit.SetAssemble True
                Line_ToSplit.SetContinuityType 1, 1
                
                Set Line_ToSplit = DPH.AddNewExtrapolLength(Point_2, Line_ToSplit, MAC_Length)
                Line_ToSplit.BorderType = 1
                Line_ToSplit.SetAssemble True
                Line_ToSplit.SetContinuityType 1, 1
                
                
                Set Surface_ToSplit = DPH.AddNewExtrude(Line_ToSplit, MAC_Length, MAC_Length, Direction_Y)
            
            End If
            
             
            Set Spline_Tran_x(Num_Span, nDu, nLayer) = DPH.AddNewHybridSplit(Spline_Tran_x_Total(Num_Span, nLayer), Surface_ToSplit, (-1) ^ (nDu + 1))
            
        Next nDu
    Next nLayer
    
    
    'Change Spline_Tran_z_Point
    For nDu = 1 To 2
        For nDivide = 1 To Num_Divide
            For nLayer = 2 To Num_Layer - 1
            
                If nDu = 1 Then
                    Orientation = False
                Else
                    Orientation = True
                End If
                
    
                If nDivide = 1 Then
    
                    Set Spline_Tran_z_Point(Num_Span, nDu, 1, nLayer) = DPH.AddNewPointOnCurveFromPercent(Spline_Tip_Part(nLayer, 1), 0.5, Orientation)
    
                ElseIf nDivide = Num_Divide Then
    
                    Set Spline_Tran_z_Point(Num_Span, nDu, Num_Divide, nLayer) = DPH.AddNewPointOnCurveFromPercent(Spline_Tip_Part(nLayer, 3), 0.5, Not Orientation)
    
                Else
    
                    K = (nDivide - 2) / (Num_Divide - 3)
    
                    If nDu = 1 Then
    
                        Set Spline_Tran_z_Point(Num_Span, nDu, nDivide, nLayer) = DPH.AddNewPointOnCurveFromPercent(Spline_Tip_Part(nLayer, 2), K, Orientation)
    
                    Else
    
                        Set Spline_Tran_z_Point(Num_Span, nDu, nDivide, nLayer) = DPH.AddNewPointOnCurveFromPercent(Spline_Tip_Part(nLayer, 4), K, Orientation)
    
                    End If
    
                End If
        
            Next nLayer
        Next nDivide
    Next nDu


    '-----------------------------------
    'Create Spline_Tran_z
    '-----------------------------------
    Dim Spline_Tran_z(1 To MaxNum_Array, 1 To 2, 1 To 11) As Object
    
    For nSpan = 1 To Num_Span
        For nDu = 1 To 2
            For nDivide = 1 To Num_Divide
                                
                Index_DivideLayer = 2
                
                
                Set Point_1 = Spline_Tran_z_Point(nSpan, nDu, nDivide, 1)
                
                Set Spline_1 = Entity_ICEM_Subline_01.Line_NormalVector(Span(nSpan), nDu, Divide(nDivide))
                
                Set Point_2 = Spline_Tran_z_Point(nSpan, nDu, nDivide, Num_Layer)
                
                Set Spline_2 = Entity_ICEM_Subline_23.Spline_Tran_z(nSpan, nDu, nDivide)
                
                
                Set Spline_Tran_z_Outer = DPH.AddNewSpline
                
                For nLayer = Index_DivideLayer To Num_Layer - 1
                    Spline_Tran_z_Outer.AddPointWithConstraintExplicit Spline_Tran_z_Point(nSpan, nDu, nDivide, nLayer), Nothing, -1#, 1, Nothing, 0#
                Next nLayer

                Spline_Tran_z_Outer.AddPointWithConstraintFromCurve Point_2, Spline_2, 1, 1, 1 'Outer
                
                
                Set Spline_Tran_z_Inner = DPH.AddNewSpline
                
                If nDivide = 1 Or nDivide = 2 Or nDivide = Num_Divide - 1 Or nDivide = Num_Divide - 2 Or nDivide = Num_Divide Then
                    K = 0.3
                ElseIf nDivide = 3 Then
                    K = 0.5
                Else
                    K = 0.7
                End If

                Spline_Tran_z_Inner.AddPointWithConstraintFromCurve Point_1, Spline_1, K, 1, 1 'Inner

                Spline_Tran_z_Inner.AddPointWithConstraintFromCurve Spline_Tran_z_Point(nSpan, nDu, nDivide, Index_DivideLayer), Spline_Tran_z_Outer, 1, 1, 1 'Mid
                
                
                Set Spline_Tran_z(nSpan, nDu, nDivide) = DPH.AddNewJoin(Spline_Tran_z_Inner, Spline_Tran_z_Outer)
                
                'WorkObject.InsertHybridShape Spline_Tran_z(nSpan, nDU, nDivide)
                    
            Next nDivide
        Next nDu
    Next nSpan
    
    
    '-----------------------------------
    'Create Spline_Tran_y
    '-----------------------------------
    Dim Spline_Tran_y(1 To 2, 1 To 11, 1 To 10) As Object
    
    For nDu = 1 To 2
        For nDivide = 1 To Num_Divide
        
            If nDivide = 1 Or nDivide = Num_Divide Then
            
                For nLayer = 1 To Num_Layer
                    
                    If nLayer = 1 Then
                        
                        Set Spline_Tran_y(nDu, 1, nLayer) = Entity_ICEM_Subline_01.Spline_Span(nDu, 1, 2)
                        
                    ElseIf nLayer > 1 And nLayer < Num_Layer Then
        
                        Set Spline_Tran_y(nDu, nDivide, nLayer) = DPH.AddNewSpline
                        
                        For nSpan = 1 To Num_Span
                                                                 
                            If nSpan = 1 Then
                            
                                Spline_Tran_y(nDu, nDivide, nLayer).AddPointWithConstraintFromCurve Spline_Tran_z_Point(nSpan, nDu, nDivide, nLayer), Direction_Y, 0.5, 1, 1
        
                            Else
                            
                                Spline_Tran_y(nDu, nDivide, nLayer).AddPointWithConstraintExplicit Spline_Tran_z_Point(nSpan, nDu, nDivide, nLayer), Nothing, -1#, 1, Nothing, 0#
                                
                            End If
                            
                        Next nSpan
        
                    ElseIf nLayer = Num_Layer Then
        
                        Set Spline_Tran_y(nDu, nDivide, nLayer) = Entity_ICEM_Subline_23.Spline_Tran_y(nDu, nDivide, 1)
                    
                    End If

                Next nLayer
                
            End If
            
        Next nDivide
    Next nDu
    
    
    '-----------------------------------
    'Create Spline_Tran_z_Point_Reduce
    '-----------------------------------
    Dim Spline_Tran_z_Point_Reduce(1 To MaxNum_Array, 1 To 2, 1 To 11, 1 To 10) As Object
    
    Num_Layer_Reduce = 4
    
    K_Layer_3 = 0.35
    
    For nDu = 1 To 2
        For nDivide = 1 To Num_Divide
            For nLayer_Reduce = 1 To Num_Layer_Reduce

                For nSpan = 1 To Num_Span
                                    
                    If nLayer_Reduce = 1 Then
                        
                        Set Spline_Tran_z_Point_Reduce(nSpan, nDu, nDivide, nLayer_Reduce) = Spline_Tran_z_Point(nSpan, nDu, nDivide, 1)
                        
                    ElseIf nLayer_Reduce = 2 Then
                        
                        Set Spline_Tran_z_Point_Reduce(nSpan, nDu, nDivide, nLayer_Reduce) = DPH.AddNewPointOnCurveFromDistance(Spline_Tran_z(nSpan, nDu, nDivide), Length_Chord_BlockSection_2(Span(nSpan)), False)

                    ElseIf nLayer_Reduce = 3 Then
                        
                        Set Spline_Tran_z_Point_Reduce(nSpan, nDu, nDivide, nLayer_Reduce) = DPH.AddNewPointOnCurveFromPercent(Spline_Tran_z(nSpan, nDu, nDivide), K_Layer_3, False)
                        
                    ElseIf nLayer_Reduce = 4 Then
                        
                        Set Spline_Tran_z_Point_Reduce(nSpan, nDu, nDivide, nLayer_Reduce) = Spline_Tran_z_Point(nSpan, nDu, nDivide, Num_Layer)
                    
                    End If

                Next nSpan

            Next nLayer_Reduce
        Next nDivide
    Next nDu
    
    
    '-----------------------------------
    'Create Spline_Tran_x_Reduce
    '-----------------------------------
    Dim Spline_Tip_Point_Reduce(1 To 10, 1 To 22) As Object
    Dim Spline_Tip_Reduce(1 To 10, 1 To 4) As Object
    
    Dim Spline_Tran_x_Reduce_Total(1 To MaxNum_Array, 1 To 10) As Object
    Dim Spline_Tran_x_Reduce(1 To MaxNum_Array, 1 To 2, 1 To 10) As Object
    
    
    'Create Spline_Tran_x_Reduce_Total
    For nSpan = 1 To Num_Span
        For nLayer_Reduce = 1 To Num_Layer_Reduce
            
            If nLayer_Reduce = 1 Then

                Set Spline_1 = Entity_ICEM_Subline_01.Spline_SectionOffset(Span(nSpan), 1)
                Set Spline_2 = Entity_ICEM_Subline_01.Spline_SectionOffset(Span(nSpan), 2)

                Set Spline_Tran_x_Reduce_Total(nSpan, nLayer_Reduce) = DPH.AddNewJoin(Spline_1, Spline_2)
            
            ElseIf nLayer_Reduce > 1 And nLayer_Reduce < Num_Layer_Reduce Then
                
                If nSpan <> Num_Span Then

                    Set Spline_Tran_x_Reduce_Total(nSpan, nLayer_Reduce) = DPH.AddNewSpline
                    Spline_Tran_x_Reduce_Total(nSpan, nLayer_Reduce).SetClosing 1

                    For nDu = 1 To 2
                        For nDivide = 1 To Num_Divide - 1

                            If nDu = 1 Then
                                Index = nDivide
                            Else
                                Index = Num_Divide - nDivide + 1
                            End If

                            Spline_Tran_x_Reduce_Total(nSpan, nLayer_Reduce).AddPointWithConstraintExplicit Spline_Tran_z_Point_Reduce(nSpan, nDu, Index, nLayer_Reduce), Nothing, -1#, 1, Nothing, 0#

                        Next nDivide
                    Next nDu

                Else

                    nPoint = 1

                    For nDu = 1 To 2
                        For nDivide = 1 To Num_Divide - 1

                            nPoint = nPoint + 1

                            If nDu = 1 Then
                                Index = nDivide
                            Else
                                Index = Num_Divide - nDivide + 1
                            End If

                            Set Spline_Tip_Point_Reduce(nLayer_Reduce, nPoint) = Spline_Tran_z_Point_Reduce(nSpan, nDu, Index, nLayer_Reduce)

                        Next nDivide
                    Next nDu

                    Set Spline_Tip_Point_Reduce(nLayer_Reduce, 1) = Spline_Tip_Point_Reduce(nLayer_Reduce, 21)
                      
                    
                    Index = Array(999, 1, 3, 11, 13)

                    For nLine = 1 To 4

                        Set Spline_Tip_Reduce(nLayer_Reduce, nLine) = DPH.AddNewSpline
                        
                        If nLine = 1 Or nLine = 3 Then
                            Num = 3
                        Else
                            Num = 9
                        End If
                        
                        For i = 0 To Num - 1
                            Spline_Tip_Reduce(nLayer_Reduce, nLine).AddPointWithConstraintExplicit Spline_Tip_Point_Reduce(nLayer_Reduce, Index(nLine) + i), Nothing, -1#, 1, Nothing, 0#
                        Next i

                    Next nLine

                    Set Spline_Tran_x_Reduce_Total(nSpan, nLayer_Reduce) = DPH.AddNewJoin(Spline_Tip_Reduce(nLayer_Reduce, 1), Spline_Tip_Reduce(nLayer_Reduce, 2))
                    Spline_Tran_x_Reduce_Total(nSpan, nLayer_Reduce).AddElement Spline_Tip_Reduce(nLayer_Reduce, 3)
                    Spline_Tran_x_Reduce_Total(nSpan, nLayer_Reduce).AddElement Spline_Tip_Reduce(nLayer_Reduce, 4)
                    
                End If
        
            ElseIf nLayer_Reduce = Num_Layer_Reduce Then

                Set Spline_1 = Entity_ICEM_Subline_23.Spline_Tran_x(nSpan, 1, 1)
                Set Spline_2 = Entity_ICEM_Subline_23.Spline_Tran_x(nSpan, 2, 1)

                Set Spline_Tran_x_Reduce_Total(nSpan, nLayer_Reduce) = DPH.AddNewJoin(Spline_1, Spline_2)
                
            End If


            If nSpan = 1 Then

                Set Spline_Tran_x_Reduce_Total(nSpan, nLayer_Reduce) = DPH.AddNewProject(Spline_Tran_x_Reduce_Total(nSpan, nLayer_Reduce), PLANE_ZX)
                Spline_Tran_x_Reduce_Total(nSpan, nLayer_Reduce).Normal = False
                Spline_Tran_x_Reduce_Total(nSpan, nLayer_Reduce).Direction = Direction_Y

            End If

            'WorkObject.InsertHybridShape Spline_Tran_x_Reduce_Total(nSpan, nLayer_Reduce)

        Next nLayer_Reduce
    Next nSpan


    'Create Spline_Tran_x_Reduce
    For nSpan = 1 To Num_Span
        For nLayer_Reduce = 1 To Num_Layer_Reduce
            
            If nLayer_Reduce = 1 Then
                
                Set Spline_Tran_x_Reduce(nSpan, 1, nLayer_Reduce) = Entity_ICEM_Subline_01.Spline_SectionOffset(Span(nSpan), 1)
                Set Spline_Tran_x_Reduce(nSpan, 2, nLayer_Reduce) = Entity_ICEM_Subline_01.Spline_SectionOffset(Span(nSpan), 2)
                
            Else
            
                Set Point_1 = Spline_Tran_z_Point_Reduce(nSpan, 1, 1, nLayer_Reduce)
                Set Point_2 = Spline_Tran_z_Point_Reduce(nSpan, 1, Num_Divide, nLayer_Reduce)
                
                Set Line_ToSplit = DPH.AddNewLinePtPt(Point_1, Point_2)
                    
                Set Line_ToSplit = DPH.AddNewExtrapolLength(Point_1, Line_ToSplit, MAC_Length)
                Line_ToSplit.BorderType = 1
                Line_ToSplit.SetAssemble True
                Line_ToSplit.SetContinuityType 1, 1
    
                Set Line_ToSplit = DPH.AddNewExtrapolLength(Point_2, Line_ToSplit, MAC_Length)
                Line_ToSplit.BorderType = 1
                Line_ToSplit.SetAssemble True
                Line_ToSplit.SetContinuityType 1, 1
    
    
                Set Surface_ToSplit = DPH.AddNewExtrude(Line_ToSplit, MAC_Length, MAC_Length, Direction_Y)
    
    
                Set Spline_Tran_x_Reduce(nSpan, 1, nLayer_Reduce) = DPH.AddNewHybridSplit(Spline_Tran_x_Reduce_Total(nSpan, nLayer_Reduce), Surface_ToSplit, 1)
                Set Spline_Tran_x_Reduce(nSpan, 2, nLayer_Reduce) = DPH.AddNewHybridSplit(Spline_Tran_x_Reduce_Total(nSpan, nLayer_Reduce), Surface_ToSplit, -1)
                                
            End If

        Next nLayer_Reduce
    Next nSpan
    
    
    '-----------------------------------
    'Create Spline_Tran_y_Reduce
    '-----------------------------------
    Dim Spline_Tran_y_Reduce(1 To 2, 1 To 11, 1 To 10) As Object
    
    Num_Connect = UBound(Index_Layer2Connect_ICEM) - LBound(Index_Layer2Connect_ICEM) + 1

    For nDu = 1 To 2
        For nDivide = 1 To Num_Divide
            For nLayer_Reduce = 1 To Num_Layer_Reduce
                
                If nLayer_Reduce = 1 Then
                
                    Set Spline_Tran_y_Reduce(nDu, nDivide, nLayer_Reduce) = Entity_ICEM_Subline_01.Spline_Span(nDu, nDivide, 2)
                
                ElseIf nLayer_Reduce = 2 Then
                    
                    If Num_Connect = 1 Then
                    
                        Mode_SectionConnect = 1
                    
                    ElseIf Num_Connect = 2 Then
                        
                        Mode_SectionConnect = 2
                        
                        Num_PerConnect_1 = Index_Layer2Connect_ICEM(1) + 1
                        Num_PerConnect_2 = Index_Layer2Connect_ICEM(2) + 1
                    
                    ElseIf Num_Connect = 3 Then
                    
                        Mode_SectionConnect = 3
                        
                        Num_PerConnect_1 = Index_Layer2Connect_ICEM(1) + 1
                        Num_PerConnect_2 = Index_Layer2Connect_ICEM(2) + 1
                        Num_PerConnect_3 = Index_Layer2Connect_ICEM(3) + 1
                    
                    End If
                    
                    
                    If Mode_SectionConnect = 1 Then
                        
                        Set Spline_Tran_y_Reduce(nDu, nDivide, nLayer_Reduce) = DPH.AddNewSpline
                        
                        For nSpan = 1 To Num_Span
                                                             
                            If nSpan = 1 Then
                            
                                Spline_Tran_y_Reduce(nDu, nDivide, nLayer_Reduce).AddPointWithConstraintFromCurve Spline_Tran_z_Point_Reduce(nSpan, nDu, nDivide, nLayer_Reduce), Direction_Y, 0.5, 1, 1
    
                            Else
                            
                                Spline_Tran_y_Reduce(nDu, nDivide, nLayer_Reduce).AddPointWithConstraintExplicit Spline_Tran_z_Point_Reduce(nSpan, nDu, nDivide, nLayer_Reduce), Nothing, -1#, 1, Nothing, 0#
                                
                            End If
                            
                        Next nSpan
                    
                    ElseIf Mode_SectionConnect = 2 Then
                        
                        Set Spline_Tran_y_2 = DPH.AddNewSpline
                        
                        For nSpan = Num_PerConnect_1 To Num_Span
                        
                            Spline_Tran_y_2.AddPointWithConstraintExplicit Spline_Tran_z_Point_Reduce(nSpan, nDu, nDivide, nLayer_Reduce), Nothing, -1#, 1, Nothing, 0#
                        
                        Next nSpan
                        
                        
                        Set Spline_Tran_y_1 = DPH.AddNewSpline
                        
                        Spline_Tran_y_1.AddPointWithConstraintFromCurve Spline_Tran_z_Point_Reduce(1, nDu, nDivide, nLayer_Reduce), Direction_Y, 0.5, 1, 1
                        
                        For nSpan = 2 To Num_PerConnect_1 - 1
                        
                            Spline_Tran_y_1.AddPointWithConstraintExplicit Spline_Tran_z_Point_Reduce(nSpan, nDu, nDivide, nLayer_Reduce), Nothing, -1#, 1, Nothing, 0#
                        
                        Next nSpan
                        
                        Spline_Tran_y_1.AddPointWithConstraintFromCurve Spline_Tran_z_Point_Reduce(Num_PerConnect_1, nDu, nDivide, nLayer_Reduce), Spline_Tran_y_2, 0.5, 1, 1
                        
                        
                        Set Spline_Tran_y_Reduce(nDu, nDivide, nLayer_Reduce) = DPH.AddNewJoin(Spline_Tran_y_1, Spline_Tran_y_2)
                    
                    ElseIf Mode_SectionConnect = 3 Then
                        
                        Set Spline_Tran_y_2 = DPH.AddNewSpline
                        
                        For nSpan = Num_PerConnect_1 To Num_PerConnect_1 + Num_PerConnect_2 - 1
                        
                            Spline_Tran_y_2.AddPointWithConstraintExplicit Spline_Tran_z_Point_Reduce(nSpan, nDu, nDivide, nLayer_Reduce), Nothing, -1#, 1, Nothing, 0#
                        
                        Next nSpan
                        
                        
                        Set Spline_Tran_y_1 = DPH.AddNewSpline
                        
                        Spline_Tran_y_1.AddPointWithConstraintFromCurve Spline_Tran_z_Point_Reduce(1, nDu, nDivide, nLayer_Reduce), Direction_Y, 0.5, 1, 1
                        
                        For nSpan = 2 To Num_PerConnect_1 - 1
                        
                            Spline_Tran_y_1.AddPointWithConstraintExplicit Spline_Tran_z_Point_Reduce(nSpan, nDu, nDivide, nLayer_Reduce), Nothing, -1#, 1, Nothing, 0#
                        
                        Next nSpan
                        
                        Spline_Tran_y_1.AddPointWithConstraintFromCurve Spline_Tran_z_Point_Reduce(Num_PerConnect_1, nDu, nDivide, nLayer_Reduce), Spline_Tran_y_2, 0.5, 1, 1
                        
                        
                        Set Spline_Tran_y_3 = DPH.AddNewSpline
                        
                        Spline_Tran_y_3.AddPointWithConstraintFromCurve Spline_Tran_z_Point_Reduce(Num_PerConnect_1 + Num_PerConnect_2 - 1, nDu, nDivide, nLayer_Reduce), Spline_Tran_y_2, 0.5, 1, 1
                        
                        For nSpan = Num_PerConnect_1 + Num_PerConnect_2 - 1 + 1 To Num_Span
                        
                            Spline_Tran_y_3.AddPointWithConstraintExplicit Spline_Tran_z_Point_Reduce(nSpan, nDu, nDivide, nLayer_Reduce), Nothing, -1#, 1, Nothing, 0#
                        
                        Next nSpan
                        
                        Set Spline_Tran_y_Reduce(nDu, nDivide, nLayer_Reduce) = DPH.AddNewJoin(Spline_Tran_y_1, Spline_Tran_y_2)
                        Spline_Tran_y_Reduce(nDu, nDivide, nLayer_Reduce).AddElement Spline_Tran_y_3
                        
                    End If

                ElseIf nLayer_Reduce > 2 And nLayer_Reduce < Num_Layer_Reduce Then
                    
                    Set Spline_Tran_y_Reduce(nDu, nDivide, nLayer_Reduce) = DPH.AddNewSpline
                    
                    For nSpan = 1 To Num_Span
                                                             
                        If nSpan = 1 Then
                        
                            Spline_Tran_y_Reduce(nDu, nDivide, nLayer_Reduce).AddPointWithConstraintFromCurve Spline_Tran_z_Point_Reduce(nSpan, nDu, nDivide, nLayer_Reduce), Direction_Y, 0.5, 1, 1

                        Else
                        
                            Spline_Tran_y_Reduce(nDu, nDivide, nLayer_Reduce).AddPointWithConstraintExplicit Spline_Tran_z_Point_Reduce(nSpan, nDu, nDivide, nLayer_Reduce), Nothing, -1#, 1, Nothing, 0#
                            
                        End If
                        
                    Next nSpan
                
                ElseIf nLayer_Reduce = Num_Layer_Reduce Then

                    Set Spline_Tran_y_Reduce(nDu, nDivide, nLayer_Reduce) = Entity_ICEM_Subline_23.Spline_Tran_y(nDu, nDivide, 1)
                
                End If
                
            Next nLayer_Reduce
        Next nDivide
    Next nDu
    
    
    '-----------------------------------
    'Create Spline_Tran_Tip_x
    '-----------------------------------
    Dim Spline_Tran_Tip_x(1 To 10) As Object

    For nLayer = 1 To Num_Layer

        If nLayer = 1 Then

            Set Spline_Tran_Tip_x(nLayer) = Entity_ICEM_Subline_01.Spline_SectionOffset_Tip_x

        ElseIf nLayer > 1 And nLayer < Num_Layer Then

            Set Point_1 = Spline_Tran_z_Point(Num_Span, 1, 1, nLayer)
            Set Point_2 = Spline_Tran_z_Point(Num_Span, 2, Num_Divide, nLayer)

            Set Spline_1 = Spline_Tran_y(1, 1, nLayer)
            Set Spline_2 = Spline_Tran_y(2, Num_Divide, nLayer)


            Set Spline_Tran_Tip_x(nLayer) = DPH.AddNewSpline

            Spline_Tran_Tip_x(nLayer).AddPointWithConstraintFromCurve Point_1, Spline_1, 1, 1, 1
            Spline_Tran_Tip_x(nLayer).AddPointWithConstraintFromCurve Point_2, Spline_2, 1, -1, 1

        ElseIf nLayer = Num_Layer Then

            Set Spline_Tran_Tip_x(nLayer) = Entity_ICEM_Subline_23.Spline_Tran_Tip_x(1)

        End If

    Next nLayer
    
    
    '-----------------------------------
    'Create Spline_Tran_Tip_Point
    '-----------------------------------
    Dim Spline_Tran_Tip_Point(1 To 11, 1 To 10) As Object

    For nTip = 1 To Num_Divide - 4
        For nLayer = 1 To Num_Layer
            
            If nLayer = 1 Then

                Set Spline_Tran_Tip_Point(nTip, nLayer) = Entity_ICEM_Subline_01.Spline_SectionOffset_Tip_Point(nTip, 2)

            ElseIf nLayer > 1 And nLayer < Num_Layer Then
                
                nDivide = nTip + 2
                
                K = (nDivide - 2) / (Num_Divide - 3)
    
                Set Spline_Tran_Tip_Point(nTip, nLayer) = DPH.AddNewPointOnCurveFromPercent(Spline_Tran_Tip_x(nLayer), K, False)
                
            ElseIf nLayer = Num_Layer Then
    
                Set Spline_Tran_Tip_Point(nTip, nLayer) = Entity_ICEM_Subline_23.Spline_Tran_Tip_Point(nTip, 1)
    
            End If
        
        Next nLayer
    Next nTip
    
    
    '-----------------------------------
    'Create Spline_Tran_Tip_z
    '-----------------------------------
    Dim Spline_Tran_Tip_z(1 To 11) As Object

    
    For nTip = 1 To Num_Divide - 4
    
        Index_DivideLayer = 2
        
        nDivide = nTip + 2
        
        
        Set Point_1 = Spline_Tran_Tip_Point(nTip, 1)
    
        Set Spline_1 = Entity_ICEM_Subline_01.Line_NormalVector_Tip(nDivide)
    
        Set Point_2 = Spline_Tran_Tip_Point(nTip, Num_Layer)
    
        Set Spline_2 = Entity_ICEM_Subline_23.Spline_Tran_Tip_z(nTip)
    
    
        Set Spline_Tran_Tip_z_Outer = DPH.AddNewSpline
    
        For nLayer = Index_DivideLayer To Num_Layer - 1
            Spline_Tran_Tip_z_Outer.AddPointWithConstraintExplicit Spline_Tran_Tip_Point(nTip, nLayer), Nothing, -1#, 1, Nothing, 0#
        Next nLayer
    
        Spline_Tran_Tip_z_Outer.AddPointWithConstraintFromCurve Point_2, Spline_2, 1, 1, 1 'Outer
                
        
        If nTip = 1 Or nTip = Num_Divide - 4 Or nTip = Num_Divide - 5 Then
            K = 0.3
        ElseIf nTip = 2 Then
            K = 0.5
        Else
            K = 0.7
        End If
                
        Set Spline_Tran_Tip_z_Inner = DPH.AddNewSpline
                           
        Spline_Tran_Tip_z_Inner.AddPointWithConstraintFromCurve Point_1, Spline_1, K, 1, 1 'Inner

        Spline_Tran_Tip_z_Inner.AddPointWithConstraintFromCurve Spline_Tran_Tip_Point(nTip, Index_DivideLayer), Spline_Tran_Tip_z_Outer, 1, 1, 1 'Mid
    
    
        Set Spline_Tran_Tip_z(nTip) = DPH.AddNewJoin(Spline_Tran_Tip_z_Inner, Spline_Tran_Tip_z_Outer)
        
        'WorkObject.InsertHybridShape Spline_Tran_Tip_z(nTip)
    
    Next nTip
    
          
    '-----------------------------------
    'Create Spline_Tran_Tip_Point_Reduce
    '-----------------------------------
    Dim Spline_Tran_Tip_Point_Reduce(1 To 11, 1 To 10) As Object
    
    For nTip = 1 To Num_Divide - 4
        For nLayer_Reduce = 1 To Num_Layer_Reduce
                                
            If nLayer_Reduce = 1 Then
                
                Set Spline_Tran_Tip_Point_Reduce(nTip, nLayer_Reduce) = Spline_Tran_Tip_Point(nTip, 1)
                
            ElseIf nLayer_Reduce = 2 Then
                
                Set Spline_Tran_Tip_Point_Reduce(nTip, nLayer_Reduce) = DPH.AddNewPointOnCurveFromDistance(Spline_Tran_Tip_z(nTip), Length_Chord_BlockSection_2(Num_Section * 3 - 2), False)

            ElseIf nLayer_Reduce = 3 Then
                
                Set Spline_Tran_Tip_Point_Reduce(nTip, nLayer_Reduce) = DPH.AddNewPointOnCurveFromPercent(Spline_Tran_Tip_z(nTip), K_Layer_3, False)
                
            ElseIf nLayer_Reduce = 4 Then
                
                Set Spline_Tran_Tip_Point_Reduce(nTip, nLayer_Reduce) = Spline_Tran_Tip_Point(nTip, Num_Layer)
            
            End If

        Next nLayer_Reduce
    Next nTip
    
    
    '-----------------------------------
    'Create Spline_Tran_Tip_x_Reduce
    '-----------------------------------
    Dim Spline_Tran_Tip_x_Reduce(1 To 10) As Object

    For nLayer_Reduce = 1 To Num_Layer_Reduce

        If nLayer_Reduce = 1 Then

            Set Spline_Tran_Tip_x_Reduce(nLayer_Reduce) = Entity_ICEM_Subline_01.Spline_SectionOffset_Tip_x

        ElseIf nLayer_Reduce > 1 And nLayer_Reduce < Num_Layer_Reduce Then

            Set Point_1 = Spline_Tran_z_Point_Reduce(Num_Span, 1, 1, nLayer_Reduce)
            Set Point_2 = Spline_Tran_z_Point_Reduce(Num_Span, 2, Num_Divide, nLayer_Reduce)
            
            Set Spline_1 = Spline_Tran_y_Reduce(1, 1, nLayer_Reduce)
            Set Spline_2 = Spline_Tran_y_Reduce(2, Num_Divide, nLayer_Reduce)
            
            
            Set Spline_Tran_Tip_x_Reduce(nLayer_Reduce) = DPH.AddNewSpline

            Spline_Tran_Tip_x_Reduce(nLayer_Reduce).AddPointWithConstraintFromCurve Point_1, Spline_1, 1, 1, 1
            
            For nTip = 1 To Num_Divide - 4
                Spline_Tran_Tip_x_Reduce(nLayer_Reduce).AddPointWithConstraintExplicit Spline_Tran_Tip_Point_Reduce(nTip, nLayer_Reduce), Nothing, -1#, 1, Nothing, 0#
            Next nTip

            Spline_Tran_Tip_x_Reduce(nLayer_Reduce).AddPointWithConstraintFromCurve Point_2, Spline_2, 1, -1, 1

        ElseIf nLayer_Reduce = Num_Layer_Reduce Then

            Set Spline_Tran_Tip_x_Reduce(nLayer_Reduce) = Entity_ICEM_Subline_23.Spline_Tran_Tip_x(1)

        End If

    Next nLayer_Reduce
    

    '-----------------------------------
    'Create Spline_Tran_Tip_y_Reduce
    '-----------------------------------
    Dim Spline_Tran_Tip_y_Reduce(1 To 11, 1 To 10) As Object
    
    For nTip = 1 To Num_Divide - 4
        For nLayer_Reduce = 1 To Num_Layer_Reduce
            
            If nLayer_Reduce = 1 Then
                
                nDivide = nTip + 2
                
                Set Spline_Tran_Tip_y_Reduce(nTip, nLayer_Reduce) = Entity_ICEM_Subline_01.Spline_SectionOffset_Tip_y(nDivide)
                
            ElseIf nLayer_Reduce > 1 And nLayer_Reduce < Num_Layer_Reduce Then
                
                nDivide = nTip + 2
                
                Set Point_1 = Spline_Tran_z_Point_Reduce(Num_Span, 1, nDivide, nLayer_Reduce)
                Set Point_2 = Spline_Tran_z_Point_Reduce(Num_Span, 2, nDivide, nLayer_Reduce)
        
                Set Spline_1 = Spline_Tran_y_Reduce(1, nDivide, nLayer_Reduce)
                Set Spline_2 = Spline_Tran_y_Reduce(2, nDivide, nLayer_Reduce)
        
        
                Set Spline_Tran_Tip_y_Reduce(nTip, nLayer_Reduce) = DPH.AddNewSpline
        
                Spline_Tran_Tip_y_Reduce(nTip, nLayer_Reduce).AddPointWithConstraintFromCurve Point_1, Spline_1, 0.5, 1, 1
                
                Spline_Tran_Tip_y_Reduce(nTip, nLayer_Reduce).AddPointWithConstraintExplicit Spline_Tran_Tip_Point_Reduce(nTip, nLayer_Reduce), Nothing, -1#, 1, Nothing, 0#
                
                Spline_Tran_Tip_y_Reduce(nTip, nLayer_Reduce).AddPointWithConstraintFromCurve Point_2, Spline_2, 0.5, -1, 1
        
            ElseIf nLayer_Reduce = Num_Layer_Reduce Then
            
                Set Spline_Tran_Tip_y_Reduce(nTip, nLayer_Reduce) = Entity_ICEM_Subline_23.Spline_Tran_Tip_y(nTip, 1)
                
            End If
    
        Next nLayer_Reduce
    Next nTip
    
        
    '-----------------------------------
    'Smooth
    '-----------------------------------
    'Spline_Tran_x_Reduce
    For nDu = 1 To 2
        For nLayer_Reduce = 1 To Num_Layer_Reduce
            
            If nLayer_Reduce <> 1 Then
                Set Spline_Tran_x_Reduce(Num_Span, nDu, nLayer_Reduce) = DPH.AddNewCurveSmooth(Spline_Tran_x_Reduce(Num_Span, nDu, nLayer_Reduce))
                Spline_Tran_x_Reduce(Num_Span, nDu, nLayer_Reduce).SetMaximumDeviation 0.001
                Spline_Tran_x_Reduce(Num_Span, nDu, nLayer_Reduce).CorrectionMode = 3
            End If

        Next nLayer_Reduce
    Next nDu
    
    
    'Spline_Tran_y_Reduce
    For nDu = 1 To 2
        For nDivide = 1 To Num_Divide
            For nLayer_Reduce = 1 To Num_Layer_Reduce
                
                If nLayer_Reduce <> 1 Then
                    Set Spline_Tran_y_Reduce(nDu, nDivide, nLayer_Reduce) = DPH.AddNewCurveSmooth(Spline_Tran_y_Reduce(nDu, nDivide, nLayer_Reduce))
                    Spline_Tran_y_Reduce(nDu, nDivide, nLayer_Reduce).SetMaximumDeviation 0.001
                    Spline_Tran_y_Reduce(nDu, nDivide, nLayer_Reduce).CorrectionMode = 3
                End If
    
            Next nLayer_Reduce
        Next nDivide
    Next nDu
    
    
    'Spline_Tran_z
    For nSpan = 1 To Num_Span
        For nDu = 1 To 2
            For nDivide = 1 To Num_Divide
            
                Set Spline_Tran_z(nSpan, nDu, nDivide) = DPH.AddNewCurveSmooth(Spline_Tran_z(nSpan, nDu, nDivide))
                Spline_Tran_z(nSpan, nDu, nDivide).SetMaximumDeviation 0.001
                Spline_Tran_z(nSpan, nDu, nDivide).CorrectionMode = 3

            Next nDivide
        Next nDu
    Next nSpan
    
    
    'Spline_Tran_Tip_z
    For nTip = 1 To Num_Divide - 4
    
        Set Spline_Tran_Tip_z(nTip) = DPH.AddNewCurveSmooth(Spline_Tran_Tip_z(nTip))
        Spline_Tran_Tip_z(nTip).SetMaximumDeviation 0.001
        Spline_Tran_Tip_z(nTip).CorrectionMode = 3
        
    Next nTip
    

    '-----------------------------------
    'Extract
    '-----------------------------------
    'Spline_Tran_z_Point_Reduce
    Set Extract_Spline_Tran_z_Point_Reduce = DPH.AddNewExtractMulti(EmptyObject)
    Set Extract_Spline_Tran_z_Point_Reduce_Repeat = DPH.AddNewExtractMulti(EmptyObject)

    For nSpan = 1 To Num_Span
        For nDu = 1 To 2
            For nDivide = 1 To Num_Divide
                For nLayer_Reduce = 1 To Num_Layer_Reduce
                
                nSection = Int(Span(nSpan) / 3) + 1
                    
                If Not IsInArray(nSection, Index_NonActSection_ICEM) Then
                
                    If Not ((nDu = 2 And nDivide = 1) Or (nDu = 2 And nDivide = Num_Divide)) Then
    
                        Extract_Spline_Tran_z_Point_Reduce.AddConstraintTolerant Spline_Tran_z_Point_Reduce(nSpan, nDu, nDivide, nLayer_Reduce), 3, False, False, 0.1, 0.5, 0.98, 1
                        Extract_Spline_Tran_z_Point_Reduce.SetElement 1, Spline_Tran_z_Point_Reduce(nSpan, nDu, nDivide, nLayer_Reduce)
                        
                    Else
                    
                        Extract_Spline_Tran_z_Point_Reduce_Repeat.AddConstraintTolerant Spline_Tran_z_Point_Reduce(nSpan, nDu, nDivide, nLayer_Reduce), 3, False, False, 0.1, 0.5, 0.98, 1
                        Extract_Spline_Tran_z_Point_Reduce_Repeat.SetElement 1, Spline_Tran_z_Point_Reduce(nSpan, nDu, nDivide, nLayer_Reduce)
                        
                    End If
                
                End If

                Next nLayer_Reduce
            Next nDivide
        Next nDu
    Next nSpan

    WorkObject.InsertHybridShape Extract_Spline_Tran_z_Point_Reduce
    WorkObject.InsertHybridShape Extract_Spline_Tran_z_Point_Reduce_Repeat
    
    Extract_Spline_Tran_z_Point_Reduce.Name = "Spline_Tran_z_Point_Reduce"
    Extract_Spline_Tran_z_Point_Reduce_Repeat.Name = "Spline_Tran_z_Point_Reduce_Repeat"
    
    
    'Spline_Tran_Tip_Point_Reduce
    Set Extract_Spline_Tran_Tip_Point_Reduce = DPH.AddNewExtractMulti(EmptyObject)

    For nTip = 1 To 7
        For nLayer_Reduce = 1 To Num_Layer_Reduce

            Extract_Spline_Tran_Tip_Point_Reduce.AddConstraintTolerant Spline_Tran_Tip_Point_Reduce(nTip, nLayer_Reduce), 3, False, False, 0.1, 0.5, 0.98, 1
            Extract_Spline_Tran_Tip_Point_Reduce.SetElement 1, Spline_Tran_Tip_Point_Reduce(nTip, nLayer_Reduce)

        Next nLayer_Reduce
    Next nTip

    WorkObject.InsertHybridShape Extract_Spline_Tran_Tip_Point_Reduce

    Extract_Spline_Tran_Tip_Point_Reduce.Name = "Spline_Tran_Tip_Point_Reduce"
    
    
    'Spline_Tran_x_Reduce
    Set Extract_Spline_Tran_x_Reduce = DPH.AddNewExtractMulti(EmptyObject)
    
    For nSpan = 1 To Num_Span
        For nDu = 1 To 2
            For nLayer_Reduce = 1 To Num_Layer_Reduce
                
                nSection = Int(Span(nSpan) / 3) + 1
                    
                If Not IsInArray(nSection, Index_NonActSection_ICEM) Then
                
                    Extract_Spline_Tran_x_Reduce.AddConstraintTolerant Spline_Tran_x_Reduce(nSpan, nDu, nLayer_Reduce), 3, False, False, 0.1, 0.5, 0.98, 1
                    Extract_Spline_Tran_x_Reduce.SetElement 1, Spline_Tran_x_Reduce(nSpan, nDu, nLayer_Reduce)
                
                End If
                
            Next nLayer_Reduce
        Next nDu
    Next nSpan
    
    WorkObject.InsertHybridShape Extract_Spline_Tran_x_Reduce
        
    Extract_Spline_Tran_x_Reduce.Name = "Spline_Tran_x_Reduce"
    

    'Spline_Tran_y_Reduce
    Set Extract_Spline_Tran_y_Reduce = DPH.AddNewExtractMulti(EmptyObject)
    
    For nDu = 1 To 2
        For nDivide = 1 To Num_Divide
            For nLayer_Reduce = 1 To Num_Layer_Reduce
                
                If Not ((nDu = 2 And nDivide = 1) Or (nDu = 2 And nDivide = Num_Divide)) Then
                
                    Extract_Spline_Tran_y_Reduce.AddConstraintTolerant Spline_Tran_y_Reduce(nDu, nDivide, nLayer_Reduce), 3, False, False, 0.1, 0.5, 0.98, 1
                    Extract_Spline_Tran_y_Reduce.SetElement 1, Spline_Tran_y_Reduce(nDu, nDivide, nLayer_Reduce)
                
                End If
                
            Next nLayer_Reduce
        Next nDivide
    Next nDu
    
    WorkObject.InsertHybridShape Extract_Spline_Tran_y_Reduce
    
    Extract_Spline_Tran_y_Reduce.Name = "Spline_Tran_y_Reduce"
    
    
    'Spline_Tran_z
    Set Extract_Spline_Tran_z = DPH.AddNewExtractMulti(EmptyObject)
    
    For nSpan = 1 To Num_Span
        For nDu = 1 To 2
            For nDivide = 1 To Num_Divide
            
                nSection = Int(Span(nSpan) / 3) + 1
                    
                If Not IsInArray(nSection, Index_NonActSection_ICEM) Then

                    If Not ((nDu = 2 And nDivide = 1) Or (nDu = 2 And nDivide = Num_Divide)) Then
    
                        Extract_Spline_Tran_z.AddConstraintTolerant Spline_Tran_z(nSpan, nDu, nDivide), 3, False, False, 0.1, 0.5, 0.98, 1
                        Extract_Spline_Tran_z.SetElement 1, Spline_Tran_z(nSpan, nDu, nDivide)
    
                    End If
                
                End If

            Next nDivide
        Next nDu
    Next nSpan
    
    WorkObject.InsertHybridShape Extract_Spline_Tran_z
        
    Extract_Spline_Tran_z.Name = "Spline_Tran_z"
    
    
    'Spline_Tran_Tip_xyz
    Set Extract_Spline_Tran_Tip_xyz = DPH.AddNewExtractMulti(EmptyObject)

    For nLayer_Reduce = 1 To Num_Layer_Reduce

        Extract_Spline_Tran_Tip_xyz.AddConstraintTolerant Spline_Tran_Tip_x_Reduce(nLayer_Reduce), 3, False, False, 0.1, 0.5, 0.98, 1
        Extract_Spline_Tran_Tip_xyz.SetElement 1, Spline_Tran_Tip_x_Reduce(nLayer_Reduce)
        
    Next nLayer_Reduce
    
    For nTip = 1 To 7
        For nLayer_Reduce = 1 To Num_Layer_Reduce
    
            Extract_Spline_Tran_Tip_xyz.AddConstraintTolerant Spline_Tran_Tip_y_Reduce(nTip, nLayer_Reduce), 3, False, False, 0.1, 0.5, 0.98, 1
            Extract_Spline_Tran_Tip_xyz.SetElement 1, Spline_Tran_Tip_y_Reduce(nTip, nLayer_Reduce)
            
        Next nLayer_Reduce
    Next nTip
    
    For nTip = 1 To 7
    
        Extract_Spline_Tran_Tip_xyz.AddConstraintTolerant Spline_Tran_Tip_z(nTip), 3, False, False, 0.1, 0.5, 0.98, 1
        Extract_Spline_Tran_Tip_xyz.SetElement 1, Spline_Tran_Tip_z(nTip)

    Next nTip
    
    WorkObject.InsertHybridShape Extract_Spline_Tran_Tip_xyz

    Extract_Spline_Tran_Tip_xyz.Name = "Spline_Tran_Tip_xyz"
    
    
    'Hide
    DocumentObject.Selection.Add Extract_Spline_Tran_z_Point_Reduce_Repeat
    
    DocumentObject.Selection.VisProperties.SetShow 1
    DocumentObject.Selection.Clear
    
    
    '-----------------------------------
    'Return
    '-----------------------------------
    ICEM_Subline_12.Num_Divide = Num_Divide
    
    ReDim ICEM_Subline_12.Span(1 To Num_Span)
    For nSpan = 1 To Num_Span
        ICEM_Subline_12.Span(nSpan) = Span(nSpan)
    Next nSpan
    
    ICEM_Subline_12.Num_Span = Num_Span
    
    
    ICEM_Subline_12.Num_Layer_Reduce = Num_Layer_Reduce


    ReDim ICEM_Subline_12.Spline_Tran_z_Point_Reduce(1 To Num_Span, 1 To 2, 1 To Num_Divide, 1 To Num_Layer_Reduce) As Object
    For nSpan = 1 To Num_Span
        For nDu = 1 To 2
            For nDivide = 1 To Num_Divide
                For nLayer_Reduce = 1 To Num_Layer_Reduce

                    Set ICEM_Subline_12.Spline_Tran_z_Point_Reduce(nSpan, nDu, nDivide, nLayer_Reduce) = Spline_Tran_z_Point_Reduce(nSpan, nDu, nDivide, nLayer_Reduce)

                Next nLayer_Reduce
            Next nDivide
        Next nDu
    Next nSpan


    ReDim ICEM_Subline_12.Spline_Tran_Tip_Point_Reduce(1 To Num_Divide - 4, 1 To Num_Layer_Reduce)
    For nTip = 1 To Num_Divide - 4
        For nLayer_Reduce = 1 To Num_Layer_Reduce

            Set ICEM_Subline_12.Spline_Tran_Tip_Point_Reduce(nTip, nLayer_Reduce) = Spline_Tran_Tip_Point_Reduce(nTip, nLayer_Reduce)

        Next nLayer_Reduce
    Next nTip
    
    
    Set ICEM_Subline_12.Extract_Spline_Tran_z_Point_Reduce = Extract_Spline_Tran_z_Point_Reduce
    Set ICEM_Subline_12.Extract_Spline_Tran_Tip_Point_Reduce = Extract_Spline_Tran_Tip_Point_Reduce
    Set ICEM_Subline_12.Extract_Spline_Tran_x_Reduce = Extract_Spline_Tran_x_Reduce
    Set ICEM_Subline_12.Extract_Spline_Tran_y_Reduce = Extract_Spline_Tran_y_Reduce
    Set ICEM_Subline_12.Extract_Spline_Tran_z = Extract_Spline_Tran_z
    Set ICEM_Subline_12.Extract_Spline_Tran_Tip_xyz = Extract_Spline_Tran_Tip_xyz
    
End Function

Attribute VB_Name = "Geometry_SmoothAndJoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'SmoothAndJoint
'*****************************
Function SmoothAndJoint(ByVal DocumentObject As Object, _
                        ByRef Entity_GenWing_WithTrail As Type_GenWing_WithTrail, ByRef Entity_DefDirection As Type_DefDirection, _
                        ByVal Data_SectionPoint As Variant, ByVal Num_Section As Integer, ByVal Num_PointPerSpline As Integer, ByVal Diameter_Fillet As Double, _
                        ByVal Act_Demo As Integer) _
                        As Type_SmoothAndJoint
            
    'Get WorkObject
    Set WorkObject = DocumentObject.Part.OrderedGeometricalSets.Item("PLANE")
    
    
    Set DPH = DocumentObject.Part.HybridShapeFactory
    
    Num_Spline = Num_Section * 2
    
    Dim EmptyObject As Object
    Dim XYZ_Cache(2)
     
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
        
    Deviation_Bridge = 0.01
    
    
    '-----------------------------------
    'Define
    '-----------------------------------
    'Length_Chord
    Dim Length_Chord(1 To MaxNum_Array) As Double
    
    For nSection = 1 To Num_Section
        
        X1_Lead = Data_SectionPoint((nSection - 1) * Num_PointPerSpline + 1, 1)
        Z1_Lead = Data_SectionPoint((nSection - 1) * Num_PointPerSpline + 1, 3)
        
        X1_Trail = (Data_SectionPoint(nSection * Num_PointPerSpline, 1) + Data_SectionPoint((Num_Spline - nSection + 1) * Num_PointPerSpline, 1)) / 2
        Z1_Trail = (Data_SectionPoint(nSection * Num_PointPerSpline, 3) + Data_SectionPoint((Num_Spline - nSection + 1) * Num_PointPerSpline, 3)) / 2
        
        Length_Chord(nSection) = Sqr((X1_Lead - X1_Trail) ^ 2 + (Z1_Lead - Z1_Trail) ^ 2)
                       
    Next nSection
    
    
    'Rate
    Rate_Offset_Span = 0.25
    Rate_Offset_Chord = 0.1
    
    Rate_Offset_Root = 1 / 11
    Rate_Offset_Panel = 1 / 7
    
    
'-----------------------------------
'Smooth_Root & Panel
'-----------------------------------
    Dim Orientation_Fillet(1 To MaxNum_Array) As Boolean

    Dim Length_Offset_Inside(1 To MaxNum_Array) As Double
    Dim Length_Offset_Outside(1 To MaxNum_Array) As Double
    
    Dim Surface_UpLow_ForSplit(1 To MaxNum_Array) As Object
    Dim Surface_Fillet_ForSplit(1 To MaxNum_Array) As Object
    
    Dim Point(1 To MaxNum_Array, 1 To 3) As Object
    Dim Spline_ToSplit(1 To MaxNum_Array) As Object
    Dim Spline_ToSplit_ForExport(1 To MaxNum_Array) As Object
    
    Dim Spline_Project_UpLow(1 To MaxNum_Array) As Object
    Dim Spline_Project_Fillet(1 To MaxNum_Array) As Object
    
    Dim Surface_Extrude(1 To MaxNum_Array) As Object
    
    Dim Surface_Split_UpLow(1 To MaxNum_Array) As Object
    Dim Surface_Split_UpLow_Final(1 To MaxNum_Array) As Object
    Dim Surface_Split_Fillet(1 To MaxNum_Array) As Object
    Dim Surface_Split_Fillet_Final(1 To MaxNum_Array) As Object
    
    Dim Surface_Bridge_UpLow(1 To MaxNum_Array) As Object
    Dim Surface_Bridge_UpLow_Final(1 To MaxNum_Array) As Object
    Dim Surface_Bridge_Fillet(1 To MaxNum_Array) As Object
    Dim Surface_Bridge_Fillet_Final(1 To MaxNum_Array) As Object
    
    
'-----------------------------------
'Smooth_Root
'-----------------------------------
    Span_Outside = Data_SectionPoint(Num_PointPerSpline + 1, 2) - Data_SectionPoint(Num_PointPerSpline, 2)

    Length_Chord_Root = Length_Chord(1)
    
    Length_1 = Rate_Offset_Span * Span_Outside
    Length_2 = Rate_Offset_Chord * Length_Chord_Root
    
    If Length_1 < Length_2 Then
        Length_Offset_Outside(1) = Length_1
    Else
        Length_Offset_Outside(1) = Length_2
    End If
    
    
    Set Extract_Cache = DPH.AddNewExtractMulti(EmptyObject)
    WorkObject.InsertHybridShape Extract_Cache
    

    '-----------------------------------
    'Pretreat
    '-----------------------------------
    Set Surface_UpLow_ForSplit(1) = DPH.AddNewSymmetry(Entity_GenWing_WithTrail.Surface_UpLow(1), PLANE_ZX)
    
    Set Surface_UpLow_ForSplit(2) = Entity_GenWing_WithTrail.Surface_UpLow(1)
    
    Set Surface_UpLow_ForSplit(3) = Entity_GenWing_WithTrail.Surface_UpLow((Num_Section - 1) * 2)
    
    Set Surface_UpLow_ForSplit(4) = DPH.AddNewSymmetry(Entity_GenWing_WithTrail.Surface_UpLow((Num_Section - 1) * 2), PLANE_ZX)
    
    
    Set Surface_Fillet_ForSplit(1) = DPH.AddNewSymmetry(Entity_GenWing_WithTrail.Surface_Fillet(1), PLANE_ZX)
    
    Set Surface_Fillet_ForSplit(2) = Entity_GenWing_WithTrail.Surface_Fillet(1)


    If Act_Demo = 1 Then
        WorkObject.InsertHybridShape Surface_UpLow_ForSplit(1)
        WorkObject.InsertHybridShape Surface_UpLow_ForSplit(4)
        
        WorkObject.InsertHybridShape Surface_Fillet_ForSplit(1)
    End If
    
    
    '-----------------------------------
    'Create Point
    '-----------------------------------
    Dx = Data_SectionPoint(Num_PointPerSpline, 1) - Data_SectionPoint(1, 1)
    Dz = Data_SectionPoint(Num_PointPerSpline, 3) - Data_SectionPoint(1, 3)

    For nLR = 1 To 2
    
        X1 = Data_SectionPoint(1, 1)
        Y1 = Data_SectionPoint(1, 2) + Length_Offset_Outside(1) * Rate_Offset_Root * (-1) ^ nLR
        Z1 = Data_SectionPoint(1, 3)
    
        Set Point(nLR, 1) = DPH.AddNewPointCoord(X1, Y1, Z1)
    
        X1 = Data_SectionPoint(1, 1) + Dx * 0.5
        Y1 = Data_SectionPoint(1, 2) + Length_Offset_Outside(1) * (-1) ^ nLR
        Z1 = Data_SectionPoint(1, 3) + Dz * 0.5
    
        Set Point(nLR, 2) = DPH.AddNewPointCoord(X1, Y1, Z1)
    
        X1 = Data_SectionPoint(Num_PointPerSpline, 1)
        Y1 = Data_SectionPoint(Num_PointPerSpline, 2) + Length_Offset_Outside(1) * Rate_Offset_Root * (-1) ^ nLR
        Z1 = Data_SectionPoint(Num_PointPerSpline, 3)
        
        Set Point(nLR, 3) = DPH.AddNewPointCoord(X1, Y1, Z1)
    
    Next nLR
    

    '-----------------------------------
    'Create Spline_ToSplit
    '-----------------------------------
    For i = 1 To 2
        
        Set Spline_ToSplit(i) = DPH.AddNewSpline
        For nPoint = 1 To 3
            Spline_ToSplit(i).AddPointWithConstraintExplicit Point(i, nPoint), Nothing, -1#, 1, Nothing, 0#
        Next nPoint
    
        Spline_ToSplit(i).SetSplineType 0
        Spline_ToSplit(i).SetClosing 0
        
    Next i


    For i = 1 To 4
        
        Index = -Int(-(i / 2))
        
        Set Point_1 = DPH.AddNewPointOnCurveFromPercent(Spline_ToSplit(Index), IIf((-1) ^ i > 0, 0, 1), False)
        
        Set Spline_ToSplit(Index) = DPH.AddNewExtrapolLength(Point_1, Spline_ToSplit(Index), 0.04 * Length_Chord_Root)
        Spline_ToSplit(Index).BorderType = 1
        Spline_ToSplit(Index).SetAssemble True
        Spline_ToSplit(Index).SetContinuityType 1, 1

    Next i
        
        
    If Act_Demo = 1 Then
        WorkObject.InsertHybridShape Spline_ToSplit(1)
        WorkObject.InsertHybridShape Spline_ToSplit(2)
    End If
    
    
    Set Spline_ToSplit_ForExport(1) = Spline_ToSplit(2)
    
    
    '-----------------------------------
    'Create Surface_Extrude
    '-----------------------------------
    For i = 1 To 2

        Set Surface_Extrude(i) = DPH.AddNewExtrude(Spline_ToSplit(i), 0.5 * Length_Chord_Root, 0.5 * Length_Chord_Root, Entity_DefDirection.Direction(1))
        
    Next i
    
    
    '-----------------------------------
    'Create Surface_Split
    '-----------------------------------
    Index = Array(999, 1, 2, 2, 1)
    Orientation = Array(999, -1, 1, 1, -1)
    
    
    'UpLow
    For i = 1 To 4
        
        Set SurfaceRef_Split_1 = Surface_UpLow_ForSplit(i)
        Set SurfaceRef_Split_2 = Surface_Extrude(Index(i))
    
        Set Surface_Split_UpLow(i) = DPH.AddNewHybridSplit(SurfaceRef_Split_1, SurfaceRef_Split_2, Orientation(i))
        
        If Act_Demo = 1 Then
            WorkObject.InsertHybridShape Surface_Split_UpLow(i)
        End If
        
        
        If i = 2 Or i = 3 Then
        
            nSplit_UpLow = nSplit_UpLow + 1
            
            Set Surface_Split_UpLow_Final(nSplit_UpLow) = Surface_Split_UpLow(i)

        End If
        
    Next i
    
    
    'Fillet
    For i = 1 To 2
    
        Set SurfaceRef_Split_1 = Surface_Fillet_ForSplit(i)
        Set SurfaceRef_Split_2 = Surface_Extrude(Index(i))
    
        Set Surface_Split_Fillet(i) = DPH.AddNewHybridSplit(SurfaceRef_Split_1, SurfaceRef_Split_2, Orientation(i))
        
        If Act_Demo = 1 Then
            WorkObject.InsertHybridShape Surface_Split_Fillet(i)
        End If
        

        If i > 1 Then
        
            nSplit_Fillet = nSplit_Fillet + 1
            
            Set Surface_Split_Fillet_Final(nSplit_Fillet) = Surface_Split_Fillet(i)

        End If
        
    Next i
    
    
    '-----------------------------------
    'Create Spline_Project
    '-----------------------------------
    Index = Array(999, 1, 2, 2, 1)
    
    
    'UpLow
    For i = 1 To 4
    
        Set Spline_Project_UpLow(i) = DPH.AddNewProject(Spline_ToSplit(Index(i)), Surface_UpLow_ForSplit(i))
        Spline_Project_UpLow(i).Normal = False
        Spline_Project_UpLow(i).Direction = Entity_DefDirection.Direction(1)
        
        'WorkObject.InsertHybridShape Spline_Project_UpLow(i)
        
    Next i
    
    
    'Fillet
    For i = 1 To 2
    
        Set Spline_Project_Fillet(i) = DPH.AddNewProject(Spline_ToSplit(Index(i)), Surface_Fillet_ForSplit(i))
        Spline_Project_Fillet(i).Normal = False
        Spline_Project_Fillet(i).Direction = Entity_DefDirection.Direction(1)
        
        'WorkObject.InsertHybridShape Spline_Project_Fillet(i)
        
    Next i


    '-----------------------------------
    'Create Surface_Bridge
    '-----------------------------------
    'UpLow
    For i = 1 To 2
        
        Set Surface_Bridge_UpLow(i) = DPH.AddNewBlend

        Surface_Bridge_UpLow(i).SetCurve 1, Spline_Project_UpLow(2 * i - 1)
        Surface_Bridge_UpLow(i).SetSupport 1, Surface_Split_UpLow(2 * i - 1)
        Surface_Bridge_UpLow(i).SetTransition 1, -1
        Surface_Bridge_UpLow(i).SetContinuity 1, 2
        Surface_Bridge_UpLow(i).SmoothDeviationActivity = True
        Surface_Bridge_UpLow(i).SetSmoothDeviation Deviation_Bridge

        Surface_Bridge_UpLow(i).SetCurve 2, Spline_Project_UpLow(2 * i)
        Surface_Bridge_UpLow(i).SetSupport 2, Surface_Split_UpLow(2 * i)
        Surface_Bridge_UpLow(i).SetTransition 2, 1
        Surface_Bridge_UpLow(i).SetContinuity 2, 2
        Surface_Bridge_UpLow(i).SmoothDeviationActivity = True
        Surface_Bridge_UpLow(i).SetSmoothDeviation Deviation_Bridge

        'WorkObject.InsertHybridShape Surface_Bridge_UpLow(i)

    Next i
    
    
    'Fillet
    For i = 1 To 2
        Orientation_Fillet(i) = Orientation_ForPercent_ByZ(Spline_Project_Fillet(i), DocumentObject, Extract_Cache)
    Next i
                    
                    
    Set Point_1 = DPH.AddNewPointOnCurveFromPercent(Spline_Project_Fillet(1), 0, Not Orientation_Fillet(1))
    Set Point_2 = DPH.AddNewPointOnCurveFromPercent(Spline_Project_Fillet(2), 0, Not Orientation_Fillet(2))
    
    Set Spline_Guide_1 = DPH.AddNewBoundaryOfSurface(Surface_Bridge_UpLow(1))
    Spline_Guide_1.From = Point_1
    Spline_Guide_1.FromOrientation = 1
    Spline_Guide_1.To = Point_2
    Spline_Guide_1.ToOrientation = 1
    
    
    Set Point_1 = DPH.AddNewPointOnCurveFromPercent(Spline_Project_Fillet(1), 0, Orientation_Fillet(1))
    Set Point_2 = DPH.AddNewPointOnCurveFromPercent(Spline_Project_Fillet(2), 0, Orientation_Fillet(2))
    
    Set Spline_Guide_2 = DPH.AddNewBoundaryOfSurface(Surface_Bridge_UpLow(2))
    Spline_Guide_2.From = Point_1
    Spline_Guide_2.FromOrientation = -1
    Spline_Guide_2.To = Point_2
    Spline_Guide_2.ToOrientation = 1
    
        
    Set Surface_Bridge_Fillet(1) = DPH.AddNewLoft
    
    Surface_Bridge_Fillet(1).AddSectionToLoft Spline_Project_Fillet(1), 1, Nothing
    Surface_Bridge_Fillet(1).AddSectionToLoft Spline_Project_Fillet(2), 1, Nothing
    
    Surface_Bridge_Fillet(1).SetStartSectionTangent Surface_Split_Fillet(1)
    Surface_Bridge_Fillet(1).SetEndSectionTangent Surface_Split_Fillet(2)

    Surface_Bridge_Fillet(1).AddGuideWithTangent Spline_Guide_1, Surface_Bridge_UpLow(1)
    Surface_Bridge_Fillet(1).AddGuideWithTangent Spline_Guide_2, Surface_Bridge_UpLow(2)
        
    'WorkObject.InsertHybridShape Surface_Bridge_Fillet(1)
        
        
    'Split Surface_Bridge
    For i = 1 To 2
        
        nBridge_UpLow = nBridge_UpLow + 1
        
        Set SurfaceRef_Split_1 = Surface_Bridge_UpLow(i)
        Set SurfaceRef_Split_2 = PLANE_ZX

        Set Surface_Bridge_UpLow_Split = DPH.AddNewHybridSplit(SurfaceRef_Split_1, SurfaceRef_Split_2, 1)

        Set Surface_Bridge_UpLow_Final(nBridge_UpLow) = Surface_Bridge_UpLow_Split
        
        If Act_Demo = 1 Then
            WorkObject.InsertHybridShape Surface_Bridge_UpLow_Final(nBridge_UpLow)
        End If
        
    Next i
    
    
    nBridge_Fillet = nBridge_Fillet + 1
    
    Set SurfaceRef_Split_1 = Surface_Bridge_Fillet(1)
    Set SurfaceRef_Split_2 = PLANE_ZX

    Set Surface_Bridge_Fillet_Split = DPH.AddNewHybridSplit(SurfaceRef_Split_1, SurfaceRef_Split_2, 1)

    Set Surface_Bridge_Fillet_Final(nBridge_Fillet) = Surface_Bridge_Fillet_Split
    
    If Act_Demo = 1 Then
        WorkObject.InsertHybridShape Surface_Bridge_Fillet_Final(nBridge_Fillet)
    End If


    '-----------------------------------
    'Hide
    '-----------------------------------
    If Act_Demo = 1 Then
    
        For i = 1 To 2
            DocumentObject.Selection.Add Spline_ToSplit(i)
        Next i
        
        For i = 1 To 2
            DocumentObject.Selection.Add Surface_Extrude(i)
        Next i
        
        DocumentObject.Selection.Add Surface_Split_UpLow(1)
        DocumentObject.Selection.Add Surface_Split_UpLow(4)
        
        DocumentObject.Selection.Add Surface_Split_Fillet(1)
        
    End If
    
    DocumentObject.Selection.Add Extract_Cache
    
    DocumentObject.Selection.VisProperties.SetShow 1
    DocumentObject.Selection.Clear


'-----------------------------------
'Smooth_Panel
'-----------------------------------
    For nSection = 2 To Num_Section - 1

        Span_Inside = Data_SectionPoint((nSection - 1) * Num_PointPerSpline + 1, 2) - Data_SectionPoint((nSection - 1) * Num_PointPerSpline, 2)
        Span_Outside = Data_SectionPoint(nSection * Num_PointPerSpline + 1, 2) - Data_SectionPoint(nSection * Num_PointPerSpline, 2)

        Length_Chord_Panel = Length_Chord(nSection)

        
        Length_1 = Rate_Offset_Span * Span_Inside
        Length_2 = Rate_Offset_Chord * Length_Chord_Panel
    
        If Length_1 < Length_2 Then
            Length_Offset_Inside(nSection) = Length_1
        Else
            Length_Offset_Inside(nSection) = Length_2
        End If
        
        
        Length_1 = Rate_Offset_Span * Span_Outside
        Length_2 = Rate_Offset_Chord * Length_Chord_Panel
        
        If Length_1 < Length_2 Then
            Length_Offset_Outside(nSection) = Length_1
        Else
            Length_Offset_Outside(nSection) = Length_2
        End If
        
        
        If Length_Offset_Inside(nSection) > Length_Offset_Outside(nSection) Then
            Length_Offset_Inside(nSection) = Length_Offset_Outside(nSection)
        Else
            Length_Offset_Outside(nSection) = Length_Offset_Inside(nSection)
        End If
        
        
        '-----------------------------------
        'Pretreat
        '-----------------------------------
        Set Surface_UpLow_ForSplit(1) = Surface_Split_UpLow_Final((nSection - 2) * 2 + 1)
        
        Set Surface_UpLow_ForSplit(2) = Entity_GenWing_WithTrail.Surface_UpLow(nSection)
        
        Set Surface_UpLow_ForSplit(3) = Entity_GenWing_WithTrail.Surface_UpLow(Num_Spline - nSection - 1)
        
        Set Surface_UpLow_ForSplit(4) = Surface_Split_UpLow_Final((nSection - 2) * 2 + 2)
        
        
        Set Surface_Fillet_ForSplit(1) = Surface_Split_Fillet_Final(nSection - 2 + 1)
        
        Set Surface_Fillet_ForSplit(2) = Entity_GenWing_WithTrail.Surface_Fillet(nSection)
        

        '-----------------------------------
        'Create Point
        '-----------------------------------
        Dx = Data_SectionPoint(nSection * Num_PointPerSpline, 1) - Data_SectionPoint((nSection - 1) * Num_PointPerSpline + 1, 1)
        Dz = Data_SectionPoint(nSection * Num_PointPerSpline, 3) - Data_SectionPoint((nSection - 1) * Num_PointPerSpline + 1, 3)

        
        For nLR = 1 To 2
            
            If nLR = 1 Then
                Length_Offset = Length_Offset_Inside(nSection)
            Else
                Length_Offset = Length_Offset_Outside(nSection)
            End If
            
            
            X1 = Data_SectionPoint((nSection - 1) * Num_PointPerSpline + 1, 1)
            Y1 = Data_SectionPoint((nSection - 1) * Num_PointPerSpline + 1, 2) + Length_Offset * Rate_Offset_Panel * (-1) ^ nLR
            Z1 = Data_SectionPoint((nSection - 1) * Num_PointPerSpline + 1, 3)
    
            Set Point(nLR, 1) = DPH.AddNewPointCoord(X1, Y1, Z1)
    
    
            X1 = Data_SectionPoint((nSection - 1) * Num_PointPerSpline + 1, 1) + Dx * 0.5
            Y1 = Data_SectionPoint((nSection - 1) * Num_PointPerSpline + 1, 2) + Length_Offset * (-1) ^ nLR
            Z1 = Data_SectionPoint((nSection - 1) * Num_PointPerSpline + 1, 3) + Dz * 0.5
    
            Set Point(nLR, 2) = DPH.AddNewPointCoord(X1, Y1, Z1)
    
                
            X1 = Data_SectionPoint(nSection * Num_PointPerSpline, 1)
            Y1 = Data_SectionPoint(nSection * Num_PointPerSpline, 2) + Length_Offset * Rate_Offset_Panel * (-1) ^ nLR
            Z1 = Data_SectionPoint(nSection * Num_PointPerSpline, 3)
    
            Set Point(nLR, 3) = DPH.AddNewPointCoord(X1, Y1, Z1)
 
        Next nLR


        '-----------------------------------
        'Create Spline_ToSplit
        '-----------------------------------
        For i = 1 To 2
        
            Set Spline_ToSplit(i) = DPH.AddNewSpline
            For nPoint = 1 To 3
                Spline_ToSplit(i).AddPointWithConstraintExplicit Point(i, nPoint), Nothing, -1#, 1, Nothing, 0#
            Next nPoint
        
            Spline_ToSplit(i).SetSplineType 0
            Spline_ToSplit(i).SetClosing 0
        
        Next i
        
        
        For i = 1 To 4
            
            Index = -Int(-(i / 2))
            
            Set Point_1 = DPH.AddNewPointOnCurveFromPercent(Spline_ToSplit(Index), IIf((-1) ^ i > 0, 0, 1), False)
            Set Spline_ToSplit(Index) = DPH.AddNewExtrapolLength(Point_1, Spline_ToSplit(Index), 0.04 * Length_Chord_Panel)
            
            Spline_ToSplit(Index).BorderType = 1
            Spline_ToSplit(Index).SetAssemble True
            Spline_ToSplit(Index).SetContinuityType 1, 1
            
        Next i
        
        If Act_Demo = 1 Then
            WorkObject.InsertHybridShape Spline_ToSplit(1)
            WorkObject.InsertHybridShape Spline_ToSplit(2)
        End If
        
        
        Set Spline_ToSplit_ForExport((nSection - 2) * 2 + 1 + 1) = Spline_ToSplit(1)
        Set Spline_ToSplit_ForExport((nSection - 2) * 2 + 2 + 1) = Spline_ToSplit(2)
        
        
        '-----------------------------------
        'Create Surface_Extrude
        '-----------------------------------
        For i = 1 To 2

            Set Surface_Extrude(i) = DPH.AddNewExtrude(Spline_ToSplit(i), 0.5 * Length_Chord_Panel, 0.5 * Length_Chord_Panel, Entity_DefDirection.Direction(nSection))
           
        Next i
        
        
        '-----------------------------------
        'Create Surface_Split
        '-----------------------------------
        Index = Array(999, 1, 2, 2, 1)
        Orientation = Array(999, -1, 1, 1, -1)
        
        
        'UpLow
        For i = 1 To 4
            
            Set SurfaceRef_Split_1 = Surface_UpLow_ForSplit(i)
            Set SurfaceRef_Split_2 = Surface_Extrude(Index(i))
        
            Set Surface_Split_UpLow(i) = DPH.AddNewHybridSplit(SurfaceRef_Split_1, SurfaceRef_Split_2, Orientation(i))
            
            If Act_Demo = 1 Then
                WorkObject.InsertHybridShape Surface_Split_UpLow(i)
            End If
            
            
            If i = 1 Then
                
                Set Surface_Split_UpLow_Final((nSection - 1) * 2 - 1) = Surface_Split_UpLow(i)
                
            ElseIf i = 4 Then
            
                Set Surface_Split_UpLow_Final((nSection - 1) * 2) = Surface_Split_UpLow(i)
    
            ElseIf i = 2 Or i = 3 Then
            
                nSplit_UpLow = nSplit_UpLow + 1
                
                Set Surface_Split_UpLow_Final(nSplit_UpLow) = Surface_Split_UpLow(i)
    
            End If
            
        Next i
        
        
        'Fillet
        For i = 1 To 2
        
            Set SurfaceRef_Split_1 = Surface_Fillet_ForSplit(i)
            Set SurfaceRef_Split_2 = Surface_Extrude(Index(i))
        
            Set Surface_Split_Fillet(i) = DPH.AddNewHybridSplit(SurfaceRef_Split_1, SurfaceRef_Split_2, Orientation(i))
            
            If Act_Demo = 1 Then
                WorkObject.InsertHybridShape Surface_Split_Fillet(i)
            End If
            
    
            If i = 1 Then
            
                Set Surface_Split_Fillet_Final(nSection - 1) = Surface_Split_Fillet(i)
                
            ElseIf i = 2 Then
            
                nSplit_Fillet = nSplit_Fillet + 1
                
                Set Surface_Split_Fillet_Final(nSplit_Fillet) = Surface_Split_Fillet(i)
    
            End If
            
        Next i
    

        '-----------------------------------
        'Create Spline_Project
        '-----------------------------------
        Index = Array(999, 1, 2, 2, 1)
        
        
        'UpLow
        For i = 1 To 4
        
            Set Spline_Project_UpLow(i) = DPH.AddNewProject(Spline_ToSplit(Index(i)), Surface_UpLow_ForSplit(i))
            Spline_Project_UpLow(i).Normal = False
            Spline_Project_UpLow(i).Direction = Entity_DefDirection.Direction(nSection)
            
            'WorkObject.InsertHybridShape Spline_Project_UpLow(i)
            
        Next i
        
        
        'Fillet
        For i = 1 To 2
            
            'Set Spline_Project_Fillet(i) = DPH.AddNewProject(Spline_ToSplit(Index(i)), Surface_Fillet_ForSplit(i))
            'Spline_Project_Fillet(i).Normal = False
            'Spline_Project_Fillet(i).Direction = Entity_DefDirection.Direction(nSection)
            
            Set Surface_ForIntersect = DPH.AddNewExtrude(Spline_ToSplit(Index(i)), Length_Chord(Num_Section), Length_Chord(Num_Section), Entity_DefDirection.Direction(nSection))
            
            Set Spline_Project_Fillet(i) = DPH.AddNewIntersection(Surface_Fillet_ForSplit(i), Surface_ForIntersect)
            
            'WorkObject.InsertHybridShape Spline_Project_Fillet(i)
            
        Next i


        '-----------------------------------
        'Create Surface_Bridge
        '-----------------------------------
        'UpLow
        For i = 1 To 2
            
            nBridge_UpLow = nBridge_UpLow + 1
            
            Set Surface_Bridge_UpLow(i) = DPH.AddNewBlend
    
            Surface_Bridge_UpLow(i).SetCurve 1, Spline_Project_UpLow(2 * i - 1)
            Surface_Bridge_UpLow(i).SetSupport 1, Surface_Split_UpLow(2 * i - 1)
            Surface_Bridge_UpLow(i).SetTransition 1, -1
            Surface_Bridge_UpLow(i).SetContinuity 1, 2
            Surface_Bridge_UpLow(i).SmoothDeviationActivity = True
            Surface_Bridge_UpLow(i).SetSmoothDeviation Deviation_Bridge
    
            Surface_Bridge_UpLow(i).SetCurve 2, Spline_Project_UpLow(2 * i)
            Surface_Bridge_UpLow(i).SetSupport 2, Surface_Split_UpLow(2 * i)
            Surface_Bridge_UpLow(i).SetTransition 2, 1
            Surface_Bridge_UpLow(i).SetContinuity 2, 2
            Surface_Bridge_UpLow(i).SmoothDeviationActivity = True
            Surface_Bridge_UpLow(i).SetSmoothDeviation Deviation_Bridge
            
            Set Surface_Bridge_UpLow_Final(nBridge_UpLow) = Surface_Bridge_UpLow(i)
            
            If Act_Demo = 1 Then
                WorkObject.InsertHybridShape Surface_Bridge_UpLow_Final(nBridge_UpLow)
            End If
    
        Next i
        
        
        'Fillet
        For i = 1 To 2
            Orientation_Fillet(i) = Orientation_ForPercent_ByZ(Spline_Project_Fillet(i), DocumentObject, Extract_Cache)
        Next i
                        
                        
        Set Point_1 = DPH.AddNewPointOnCurveFromPercent(Spline_Project_Fillet(1), 0, Not Orientation_Fillet(1))
        Set Point_2 = DPH.AddNewPointOnCurveFromPercent(Spline_Project_Fillet(2), 0, Not Orientation_Fillet(2))
        
        Set Spline_Guide_1 = DPH.AddNewBoundaryOfSurface(Surface_Bridge_UpLow(1))
        Spline_Guide_1.From = Point_1
        Spline_Guide_1.FromOrientation = 1
        Spline_Guide_1.To = Point_2
        Spline_Guide_1.ToOrientation = 1
        
        
        Set Point_1 = DPH.AddNewPointOnCurveFromPercent(Spline_Project_Fillet(1), 0, Orientation_Fillet(1))
        Set Point_2 = DPH.AddNewPointOnCurveFromPercent(Spline_Project_Fillet(2), 0, Orientation_Fillet(2))
        
        Set Spline_Guide_2 = DPH.AddNewBoundaryOfSurface(Surface_Bridge_UpLow(2))
        Spline_Guide_2.From = Point_1
        Spline_Guide_2.FromOrientation = -1
        Spline_Guide_2.To = Point_2
        Spline_Guide_2.ToOrientation = 1
        
            
        nBridge_Fillet = nBridge_Fillet + 1
        
        Set Surface_Bridge_Fillet_Final(nBridge_Fillet) = DPH.AddNewLoft
        
        Surface_Bridge_Fillet_Final(nBridge_Fillet).AddSectionToLoft Spline_Project_Fillet(1), 1, Nothing
        Surface_Bridge_Fillet_Final(nBridge_Fillet).AddSectionToLoft Spline_Project_Fillet(2), 1, Nothing
        
        Surface_Bridge_Fillet_Final(nBridge_Fillet).SetStartSectionTangent Surface_Split_Fillet(1)
        Surface_Bridge_Fillet_Final(nBridge_Fillet).SetEndSectionTangent Surface_Split_Fillet(2)
    
        Surface_Bridge_Fillet_Final(nBridge_Fillet).AddGuideWithTangent Spline_Guide_1, Surface_Bridge_UpLow(1)
        Surface_Bridge_Fillet_Final(nBridge_Fillet).AddGuideWithTangent Spline_Guide_2, Surface_Bridge_UpLow(2)
            
        If Act_Demo = 1 Then
            WorkObject.InsertHybridShape Surface_Bridge_Fillet_Final(nBridge_Fillet)
        End If
            
    
        '-----------------------------------
        'Hide
        '-----------------------------------
        If Act_Demo = 1 Then
        
            For i = 1 To 2
                DocumentObject.Selection.Add Spline_ToSplit(i)
            Next i
            
            For i = 1 To 2
                DocumentObject.Selection.Add Surface_Extrude(i)
            Next i
            
        End If
    
        DocumentObject.Selection.Add Extract_Cache
        
        DocumentObject.Selection.VisProperties.SetShow 1
        DocumentObject.Selection.Clear

    Next nSection
    

'-----------------------------------
'Joint
'-----------------------------------

    Set Surface_Joint_UpLow_Up = DPH.AddNewJoin(Surface_Bridge_UpLow_Final(1), Surface_Split_UpLow_Final(1))
    
    For i = 1 To Num_Section - 2
        Surface_Joint_UpLow_Up.AddElement Surface_Bridge_UpLow_Final(i * 2 + 1)
        Surface_Joint_UpLow_Up.AddElement Surface_Split_UpLow_Final(i * 2 + 1)
    Next i
    
    Surface_Joint_UpLow_Up.SetDeviation Deviation_Bridge
        
    
    Set Surface_Joint_UpLow_Low = DPH.AddNewJoin(Surface_Bridge_UpLow_Final(2), Surface_Split_UpLow_Final(2))
    
    For i = 1 To Num_Section - 2
        Surface_Joint_UpLow_Low.AddElement Surface_Bridge_UpLow_Final((i + 1) * 2)
        Surface_Joint_UpLow_Low.AddElement Surface_Split_UpLow_Final((i + 1) * 2)
    Next i
        
    Surface_Joint_UpLow_Low.SetDeviation Deviation_Bridge
    
    
    Set Surface_Joint_Fillet = DPH.AddNewJoin(Surface_Bridge_Fillet_Final(1), Surface_Split_Fillet_Final(1))
    
    For i = 1 To Num_Section - 2
        Surface_Joint_Fillet.AddElement Surface_Bridge_Fillet_Final(i + 1)
        Surface_Joint_Fillet.AddElement Surface_Split_Fillet_Final(i + 1)
    Next i
        
    
'-----------------------------------
'Deal Tip
'-----------------------------------
    
    '-----------------------------------
    'Create Direction_Tip
    '-----------------------------------
    Dim Data_QuaterPoint(1 To MaxNum_Array, 1 To 3) As Double
    Dim Dihedral(1 To MaxNum_Array, 1 To 2) As Double
    
    
    'Solve Dihedral_Tip
    For nSection = 4 To 5
        
        Dx = Data_SectionPoint(Num_PointPerSpline * nSection, 1) - Data_SectionPoint(Num_PointPerSpline * (nSection - 1) + 1, 1)
        Dy = Data_SectionPoint(Num_PointPerSpline * nSection, 2) - Data_SectionPoint(Num_PointPerSpline * (nSection - 1) + 1, 2)
        Dz = Data_SectionPoint(Num_PointPerSpline * nSection, 3) - Data_SectionPoint(Num_PointPerSpline * (nSection - 1) + 1, 3)
        
        Data_QuaterPoint(nSection, 1) = Data_SectionPoint(Num_PointPerSpline * (nSection - 1) + 1, 1) + Dx / 4
        Data_QuaterPoint(nSection, 2) = Data_SectionPoint(Num_PointPerSpline * (nSection - 1) + 1, 2) + Dy / 4
        Data_QuaterPoint(nSection, 3) = Data_SectionPoint(Num_PointPerSpline * (nSection - 1) + 1, 3) + Dz / 4
       
    Next nSection
    
        
    nSection = 5
    
    Dz = Data_QuaterPoint(nSection, 3) - Data_QuaterPoint(nSection - 1, 3)
    Dy = Data_QuaterPoint(nSection, 2) - Data_QuaterPoint(nSection - 1, 2)

    Dihedral_Tip = Atn(Dz / Dy) * 180 / Pi


    'Solve Twist_Tip
    Dx = Data_SectionPoint(Num_PointPerSpline * Num_Section, 1) - Data_SectionPoint(Num_PointPerSpline * (Num_Section - 1) + 1, 1)
    Dz = Data_SectionPoint(Num_PointPerSpline * (Num_Section - 1) + 1, 3) - Data_SectionPoint(Num_PointPerSpline * Num_Section, 3)
        
    Twist_Tip = Atn(Dz / Dx) * 180 / Pi
    
    
    'Create Direction_Dihedral
    Set Direction_Dihedral_Tip_Point = DPH.AddNewPointOnCurveFromPercent(Entity_GenWing_WithTrail.Spline_Original(Num_Section), 1, False)
        
    Set Direction_Dihedral_Tip_Line = DPH.AddNewLineAngle(Direction_Z, PLANE_YZ, Direction_Dihedral_Tip_Point, False, 0, 0.1 * Length_Chord_Root, Dihedral_Tip, True)
    
    Set Direction_Dihedral_Tip = DPH.AddNewDirection(Direction_Dihedral_Tip_Line)
    
    
    'Create Direction_Twist
    Set Direction_Twist_Tip_Point = DPH.AddNewPointOnCurveFromPercent(Entity_GenWing_WithTrail.Spline_Original(Num_Section), 1, False)
        
    Set Direction_Twist_Tip_Line = DPH.AddNewLineAngle(Direction_Z, PLANE_ZX, Direction_Dihedral_Tip_Point, False, 0, 0.1 * Length_Chord_Root, Twist_Tip, True)
    
    Set Direction_Twist_Tip = DPH.AddNewDirection(Direction_Twist_Tip_Line)

    
    '-----------------------------------
    'Split by Dihedral
    '-----------------------------------
    'Create Line_ToSplit
    If Dihedral_Tip <= 0 Then
    
        Extremum_z = Data_SectionPoint((Num_Section - 1) * Num_PointPerSpline + 1, 3)
        
        For i = 1 To Num_PointPerSpline * 2
            
            Local_z = Data_SectionPoint((Num_Section - 1) * Num_PointPerSpline + i, 3)
            
            If Local_z >= Extremum_z Then
            
                Extremum_z = Local_z
                Index_Extremum_z = i
                
            End If
    
        Next i
        
    ElseIf Dihedral_Tip > 0 Then
    
        Extremum_z = Data_SectionPoint((Num_Section - 1) * Num_PointPerSpline + 1, 3)
        
        For i = 1 To Num_PointPerSpline * 2
            
            Local_z = Data_SectionPoint((Num_Section - 1) * Num_PointPerSpline + i, 3)
            
            If Local_z <= Extremum_z Then
            
                Extremum_z = Local_z
                Index_Extremum_z = i
                
            End If
    
        Next i
        
    End If
    
    
    Max_Thickness = Abs(Sqr((Data_SectionPoint((Num_Section - 1) * Num_PointPerSpline + 1, 1) - Data_SectionPoint(Num_Section * Num_PointPerSpline + 1, 1)) ^ 2 + _
                            (Data_SectionPoint((Num_Section - 1) * Num_PointPerSpline + 1, 3) - Data_SectionPoint(Num_Section * Num_PointPerSpline + 1, 3)) ^ 2))
    
    For i = 1 To Num_PointPerSpline
        
        Local_Thickness = Abs(Sqr((Data_SectionPoint((Num_Section - 1) * Num_PointPerSpline + i, 1) - Data_SectionPoint(Num_Section * Num_PointPerSpline + i, 1)) ^ 2 + _
                                  (Data_SectionPoint((Num_Section - 1) * Num_PointPerSpline + i, 3) - Data_SectionPoint(Num_Section * Num_PointPerSpline + i, 3)) ^ 2))
        
        If Local_Thickness > Max_Thickness Then
        
            Max_Thickness = Local_Thickness
            Index_Max_Thickness = i
            
        End If

    Next i
        
  
    X1 = Data_SectionPoint((Num_Section - 1) * Num_PointPerSpline + Index_Extremum_z, 1)
    'Y1 = Data_SectionPoint((Num_Section - 1) * Num_PointPerSpline + Index_Max_z, 2) - Max_Thickness / 4 * Cos(Abs(Dihedral_Tip) / 180 * Pi)
    Y1 = Data_SectionPoint((Num_Section - 1) * Num_PointPerSpline + Index_Extremum_z, 2) - Diameter_Fillet
    Z1 = Data_SectionPoint((Num_Section - 1) * Num_PointPerSpline + Index_Extremum_z, 3)

    Set Point_1 = DPH.AddNewPointCoord(X1, Y1, Z1)
    
    Set Line_ToSplit = DPH.AddNewLinePtDir(Point_1, Direction_Dihedral_Tip, -2 * Length_Chord(Num_Section), 2 * Length_Chord(Num_Section), False)


    'Split Tip
    Set Surface_ToSplit = DPH.AddNewExtrude(Line_ToSplit, 2 * Length_Chord(Num_Section), 2 * Length_Chord(Num_Section), Direction_X)
    
    If Act_Demo = 1 Then
        WorkObject.InsertHybridShape Surface_ToSplit
    End If
    
    
    Set Surface_Joint_UpLow_Up = DPH.AddNewHybridSplit(Surface_Joint_UpLow_Up, Surface_ToSplit, -1)
    Set Surface_Joint_UpLow_Low = DPH.AddNewHybridSplit(Surface_Joint_UpLow_Low, Surface_ToSplit, -1)
    Set Surface_Joint_Fillet = DPH.AddNewHybridSplit(Surface_Joint_Fillet, Surface_ToSplit, -1)

    WorkObject.InsertHybridShape Surface_Joint_UpLow_Up
    WorkObject.InsertHybridShape Surface_Joint_UpLow_Low
    WorkObject.InsertHybridShape Surface_Joint_Fillet
    
    
    Set Extract_Surface_UpLowFillet = DPH.AddNewExtractMulti(Surface_Joint_UpLow_Up)
    
    Extract_Surface_UpLowFillet.AddConstraintTolerant Surface_Joint_UpLow_Up, 3, False, False, 0.1, 0.5, 0.98, 1
    Extract_Surface_UpLowFillet.SetElement 1, Surface_Joint_UpLow_Up
    
    Extract_Surface_UpLowFillet.AddConstraintTolerant Surface_Joint_UpLow_Low, 3, False, False, 0.1, 0.5, 0.98, 1
    Extract_Surface_UpLowFillet.SetElement 1, Surface_Joint_UpLow_Low
    
    Extract_Surface_UpLowFillet.AddConstraintTolerant Surface_Joint_Fillet, 3, False, False, 0.1, 0.5, 0.98, 1
    Extract_Surface_UpLowFillet.SetElement 1, Surface_Joint_Fillet
    
    Set Surface_Tip_Fill = DPH.AddNewHybridSplit(Surface_ToSplit, Extract_Surface_UpLowFillet, -1)
    
    'WorkObject.InsertHybridShape Surface_Tip_Fill
    
    
    '-----------------------------------
    'Create Tip
    '-----------------------------------
    Dim Divide(1 To MaxNum_Array) As Double
    
    Dim Spline_Tip_y(1 To MaxNum_Array) As Object
    Dim Spline_ForTangency(1 To MaxNum_Array) As Object
    
    
    Divide_Init = 0.14
    Num_Divide = 11
    For nDivide = 1 To Num_Divide
        Divide(nDivide) = Divide_Init + (nDivide - 1) * (1 - Divide_Init) / (Num_Divide - 1)
    Next nDivide
    
    Set Extract_Cache = DPH.AddNewExtractMulti(EmptyObject)
    WorkObject.InsertHybridShape Extract_Cache
    
    
    'Create Spline_Tip_x
    Set Spline_Tip_UpLow_Up = DPH.AddNewIntersection(Surface_Joint_UpLow_Up, Surface_ToSplit)
    Set Spline_Tip_UpLow_Low = DPH.AddNewIntersection(Surface_Joint_UpLow_Low, Surface_ToSplit)
    Set Spline_Tip_Fillet = DPH.AddNewIntersection(Surface_Joint_Fillet, Surface_ToSplit)
    
    
    'Create Spline_Tip_y
    Orientation = Orientation_ForPercent_ByX(Spline_Tip_UpLow_Up, DocumentObject, Extract_Cache)

    For nSpline = 1 To Num_Divide
        
        Set Point_1 = DPH.AddNewPointOnCurveFromPercent(Spline_Tip_UpLow_Up, Divide(nSpline), Orientation)
        
        Set Line_Tip = DPH.AddNewLinePtDir(Point_1, Direction_Y, -0.1 * Length_Chord_Root, 0.1 * Length_Chord_Root, False)
        
        Set Spline_ForTangency(1) = DPH.AddNewProject(Line_Tip, Surface_Joint_UpLow_Up)
        Spline_ForTangency(1).Normal = False
        Spline_ForTangency(1).Direction = Direction_Twist_Tip
        
        Set Spline_ForTangency(2) = DPH.AddNewProject(Line_Tip, Surface_Joint_UpLow_Low)
        Spline_ForTangency(2).Normal = False
        Spline_ForTangency(2).Direction = Direction_Twist_Tip
        
        If nSpline = Num_Divide Then
            Set Spline_ForTangency(1) = Entity_GenWing_WithTrail.Line_Guide(Num_Section - 1, 2)
            Set Spline_ForTangency(1) = DPH.AddNewHybridSplit(Spline_ForTangency(1), Surface_ToSplit, 1)

            Set Spline_ForTangency(2) = Entity_GenWing_WithTrail.Line_Guide(Num_Section - 1, 4)
            Set Spline_ForTangency(2) = DPH.AddNewHybridSplit(Spline_ForTangency(2), Surface_ToSplit, 1)
        End If
        
        'WorkObject.InsertHybridShape Spline_ForTangency(1)
        'WorkObject.InsertHybridShape Spline_ForTangency(2)
        
        
        Set Point_1 = DPH.AddNewPointOnCurveFromPercent(Spline_ForTangency(1), 0, True)
        Set Point_2 = DPH.AddNewPointOnCurveFromPercent(Spline_ForTangency(2), 0, True)
        
        Length_Line_Tip = GetDistance(Point_1, Point_2, DocumentObject, Extract_Cache)
        
        If nSpline <> Num_Divide Then
            Length_Line_Tip = 0.9 * Length_Line_Tip
        End If
        
        
        Set Line = DPH.AddNewLinePtPt(Point_1, Point_2)
        
        Set Point_Center = DPH.AddNewPointOnCurveFromPercent(Line, 0.5, False)
        
'        If nSpline <> Num_Divide Then
'
'            Set Line_NormalTip = DPH.AddNewLineNormal(Surface_Tip_Fill, Point_Center, 0, Length_Line_Tip / 2, False)
'
'        Else
'
'            Set Direction_Project = DPH.AddNewDirection(Entity_GenWing_WithTrail.Line_Guide(Num_Section - 1, 3))
'
'            Set Line_NormalTip = DPH.AddNewLinePtDir(Point_Center, Direction_Project, 0, Length_Line_Tip / 2, False)
'
'        End If

        Set Line_NormalTip = DPH.AddNewLineNormal(Surface_Tip_Fill, Point_Center, 0, Length_Line_Tip / 2, False)
        
        Set Point_3 = DPH.AddNewPointOnCurveFromPercent(Line_NormalTip, 1, False)
        
        
        Set Spline_Tip_y(nSpline) = DPH.AddNewSpline
        Spline_Tip_y(nSpline).AddPointWithConstraintFromCurve Point_1, Spline_ForTangency(1), 0.7, 1, 2
        Spline_Tip_y(nSpline).AddPointWithConstraintExplicit Point_3, Nothing, -1#, 1, Nothing, 0#
        Spline_Tip_y(nSpline).AddPointWithConstraintFromCurve Point_2, Spline_ForTangency(2), 0.7, -1, 2
        
        'WorkObject.InsertHybridShape Spline_Tip_y(nSpline)
             
    Next nSpline
    
    
    'Create Surface_Tip_Mid
    Set Spline_Guide_Mid = DPH.AddNewSpline
        
    For nSpline = 1 To Num_Divide
        
        Set Point_1 = DPH.AddNewPointOnCurveFromPercent(Spline_Tip_y(nSpline), 0.5, False)
        
        Spline_Guide_Mid.AddPointWithConstraintExplicit Point_1, Nothing, -1#, 1, Nothing, 0#
    
    Next nSpline

    
    Set Surface_Tip_Mid = DPH.AddNewLoft
        
    Surface_Tip_Mid.AddGuide Spline_Guide_Mid
    
    For nSpline = 1 To Num_Divide

        Surface_Tip_Mid.AddSectionToLoft Spline_Tip_y(nSpline), 1, Nothing
    
    Next nSpline

    Surface_Tip_Mid.AddGuideWithTangent Spline_Tip_UpLow_Up, Surface_Joint_UpLow_Up
    Surface_Tip_Mid.AddGuideWithTangent Spline_Tip_UpLow_Low, Surface_Joint_UpLow_Low
    
    'WorkObject.InsertHybridShape Surface_Tip_Mid
    
    
    'Create Surface_Tip_Lead
    Set Spline_Tip = DPH.AddNewJoin(Spline_Tip_UpLow_Up, Spline_Tip_UpLow_Low)
    Spline_Tip.AddElement Spline_Tip_Fillet
        
        
    Orientation = Orientation_ForSplit_ByX(Spline_Tip, Spline_Tip_y(1), DocumentObject, Extract_Cache)

    Set Spline_Tip_Lead = DPH.AddNewHybridSplit(Spline_Tip, Spline_Tip_y(1), Orientation)
    
    
    Set Extract_Surface_UpLow = DPH.AddNewExtractMulti(Surface_Joint_UpLow_Up)
    
    Extract_Surface_UpLow.AddConstraintTolerant Surface_Joint_UpLow_Up, 3, False, False, 0.1, 0.5, 0.98, 1
    Extract_Surface_UpLow.SetElement 1, Surface_Joint_UpLow_Up
    
    Extract_Surface_UpLow.AddConstraintTolerant Surface_Joint_UpLow_Low, 3, False, False, 0.1, 0.5, 0.98, 1
    Extract_Surface_UpLow.SetElement 1, Surface_Joint_UpLow_Low
    
    
    Set Point_1 = DPH.AddNewPointOnCurveFromPercent(Spline_Tip_UpLow_Up, 0, False)
    Set Point_2 = DPH.AddNewPointOnCurveFromPercent(Spline_Tip_y(1), 0.5, False)
    
    Set Spline_Tip_Append = DPH.AddNewSpline
    Spline_Tip_Append.AddPointWithConstraintFromCurve Point_1, Entity_GenWing_WithTrail.Line_Guide(Num_Section - 1, 1), 0.3, 1, 2
    Spline_Tip_Append.AddPointWithConstraintFromCurve Point_2, Spline_Guide_Mid, 1, 1, 2
    
    
    Set Surface_Tip_Lead = DPH.AddNewFill()
    
    Surface_Tip_Lead.AddBound Spline_Tip_Lead
    Surface_Tip_Lead.AddSupportAtBound Spline_Tip_Lead, Extract_Surface_UpLow
    Surface_Tip_Lead.SetBoundaryContinuity 1, 1
    
    Surface_Tip_Lead.AddBound Spline_Tip_y(1)
    Surface_Tip_Lead.AddSupportAtBound Spline_Tip_y(1), Surface_Tip_Mid
    Surface_Tip_Lead.SetBoundaryContinuity 1, 2
    
    Surface_Tip_Lead.AppendConstraint Spline_Tip_Append
    
    Surface_Tip_Lead.AdvancedTolerantMode = 3
    Surface_Tip_Lead.MaximumDeviationValue = 0.001
    
    'WorkObject.InsertHybridShape Surface_Tip_Lead
    
    
    'Create Surface_Tip_Trail
    Set Surface_Tip_Trail = DPH.AddNewFill()
    
    Surface_Tip_Trail.AddBound Spline_Tip_y(Num_Divide)
    Surface_Tip_Trail.AddSupportAtBound Spline_Tip_y(Num_Divide), Surface_Tip_Mid
    Surface_Tip_Trail.SetBoundaryContinuity 1, 1
    
    Surface_Tip_Trail.AddBound Spline_Tip_Fillet
    Surface_Tip_Trail.AddSupportAtBound Spline_Tip_Fillet, Surface_Joint_Fillet
    Surface_Tip_Trail.SetBoundaryContinuity 1, 2
    
    'Surface_Tip_Trail.AdvancedTolerantMode = 3
    'Surface_Tip_Trail.MaximumDeviationValue = Diameter_Fillet * 0.01
    
    'WorkObject.InsertHybridShape Surface_Tip_Trail
    
    
    'Combine
    Set Surface_Joint_Tip = DPH.AddNewJoin(Surface_Tip_Lead, Surface_Tip_Mid)
    Surface_Joint_Tip.AddElement Surface_Tip_Trail
    'Surface_Joint_Tip.SetDeviation Diameter_Fillet * 0.01
    
    WorkObject.InsertHybridShape Surface_Joint_Tip
    
    Set Surface_Joint_Tip_Front = DPH.AddNewJoin(Surface_Tip_Lead, Surface_Tip_Mid)

    
    '-----------------------------------
    'Hide
    '-----------------------------------
    If Act_Demo = 1 Then
        DocumentObject.Selection.Add Entity_GenWing_WithTrail.Surface_Tip_Fill
    End If
    
    DocumentObject.Selection.Add Surface_ToSplit
    
    DocumentObject.Selection.Add Extract_Cache
        
    DocumentObject.Selection.VisProperties.SetShow 1
    DocumentObject.Selection.Clear
    
    
'-----------------------------------
'Return
'-----------------------------------
    SmoothAndJoint.Deviation_Bridge = Deviation_Bridge
    
    
    ReDim SmoothAndJoint.Spline_UpLow(1 To MaxNum_Array)
    For i = 1 To Num_Spline
    
        Set SmoothAndJoint.Spline_UpLow(i) = Entity_GenWing_WithTrail.Spline_UpLow(i)
        
        If i = Num_Section Then
            
            Set SmoothAndJoint.Spline_UpLow(i) = Spline_Tip_UpLow_Up
        
        ElseIf i = Num_Section + 1 Then
            
            Set SmoothAndJoint.Spline_UpLow(i) = Spline_Tip_UpLow_Low
        
        End If
        
    Next i
    
    
    ReDim SmoothAndJoint.Spline_Fillet(1 To MaxNum_Array)
    For i = 1 To Num_Section
    
        Set SmoothAndJoint.Spline_Fillet(i) = Entity_GenWing_WithTrail.Spline_Fillet(i)
        
        If i = Num_Section Then
            
            Set SmoothAndJoint.Spline_Fillet(i) = Spline_Tip_Fillet
        
        End If
        
    Next i
    
    
    ReDim SmoothAndJoint.Spline_ToSplit(1 To MaxNum_Array)
    For i = 1 To (Num_Section - 2) * 2 + 1
        
        Set SmoothAndJoint.Spline_ToSplit(i) = Spline_ToSplit_ForExport(i)
    
    Next i
    
    
    ReDim SmoothAndJoint.Spline_Tip_y(1 To MaxNum_Array)
    For i = 1 To Num_Divide
        
        Set SmoothAndJoint.Spline_Tip_y(i) = Spline_Tip_y(i)
    
    Next i


    Set SmoothAndJoint.Surface_Joint_UpLow_Up = Surface_Joint_UpLow_Up
    Set SmoothAndJoint.Surface_Joint_UpLow_Low = Surface_Joint_UpLow_Low
    Set SmoothAndJoint.Surface_Joint_Fillet = Surface_Joint_Fillet
    Set SmoothAndJoint.Surface_Tip_Fill = Surface_Tip_Fill
    Set SmoothAndJoint.Surface_Joint_Tip = Surface_Joint_Tip
    Set SmoothAndJoint.Surface_Joint_Tip_Front = Surface_Joint_Tip_Front
    Set SmoothAndJoint.Surface_Joint_Tip_Trail = Surface_Tip_Trail


    ReDim SmoothAndJoint.Length_Offset_Inside(1 To MaxNum_Array) As Double
    For i = 1 To Num_Section - 1
        
        SmoothAndJoint.Length_Offset_Inside(i) = Length_Offset_Inside(i)
    
    Next i


    ReDim SmoothAndJoint.Length_Offset_Outside(1 To MaxNum_Array) As Double
    For i = 1 To Num_Section - 1
        
        SmoothAndJoint.Length_Offset_Outside(i) = Length_Offset_Outside(i)
    
    Next i

End Function

Attribute VB_Name = "MainFun"


Public Const MaxNum_Array_Point = 3000
Public Const MaxNum_Array = 100
Public Const Pi = 3.1415926


'************************************************************************
'Public Type
'************************************************************************
Public Type Type_DefDirection

    Direction() As Object
    
End Type


Public Type Type_GenWing

    Spline_UpLow() As Object
    Surface_UpLow() As Object
    Surface_Tip_Fill As Object
    
End Type


Public Type Type_GenWing_WithTrail
    
    Line_Guide() As Object
    
    Spline_Original() As Object
    
    Spline_UpLow() As Object
    Spline_Fillet() As Object
    
    Surface_UpLow() As Object
    Surface_Fillet() As Object
    Surface_Tip_Fill As Object
    
End Type


Public Type Type_GenTrail

    Angle As Double
    
    UpOrLow_AngleDivide As Integer
    
    Line_ParallelAngleDivide_1 As Object
    Line_ParallelAngleDivide_2 As Object
    
End Type


Public Type Type_SmoothAndJoint
    
    Deviation_Bridge As Double
    
    Spline_UpLow() As Object
    Spline_Fillet() As Object
    
    Spline_ToSplit() As Object
    Spline_Tip_y() As Object
    
    Surface_Joint_UpLow_Up As Object
    Surface_Joint_UpLow_Low As Object
    Surface_Joint_Fillet As Object
    Surface_Tip_Fill As Object
    Surface_Joint_Tip As Object
    Surface_Joint_Tip_Front As Object
    Surface_Joint_Tip_Trail As Object
    
    Length_Offset_Inside() As Double
    Length_Offset_Outside() As Double

End Type


Public Type Type_ICEM_FluidAndBOI
    
    Radius_Fluid As Double
    Radius_BOI_Fluid_BasedMAC As Double
    
    Surface_BOI_Fluid As Object
    Surface_Fluid As Object
    Surface_Symm As Object
    
    Extract_Surface_BOI_Fluid As Object
    Extract_Surface_Fluid As Object
    Extract_Surface_Symm As Object

End Type


Public Type Type_ICEM_Subline_01
    
    Dihedral() As Double
    
    Num_Divide As Integer
    
    Num_Span As Integer
    
    Span_BlockSection() As Double
    SpanSLength_BlockSection() As Double
    
    LayerHeight_BlockSection() As Double
    Length_Chord_BlockSection() As Double
    
    Spline_SectionOffset_Point() As Object
    Spline_SectionOffset_Tip_Point() As Object
    
    Spline_SectionProject() As Object
    Spline_SectionOffset() As Object
    
    Line_NormalVector() As Object
    Spline_Span() As Object
    
    Spline_SectionProject_Tip_x As Object
    Spline_SectionProject_Tip_y() As Object
    Spline_SectionOffset_Tip_x As Object
    Spline_SectionOffset_Tip_y() As Object
    Line_NormalVector_Tip() As Object
    
End Type


Public Type Type_ICEM_Subline_12
    
    Num_Divide As Integer
    
    Span() As Double
    Num_Span As Integer
    
    Num_Layer_Reduce As Integer
    
    Spline_Tran_z_Point_Reduce() As Object
    Spline_Tran_Tip_Point_Reduce() As Object

    Extract_Spline_Tran_z_Point_Reduce As Object
    Extract_Spline_Tran_Tip_Point_Reduce As Object
    Extract_Spline_Tran_x_Reduce As Object
    Extract_Spline_Tran_y_Reduce As Object
    Extract_Spline_Tran_z As Object
    Extract_Spline_Tran_Tip_xyz As Object
    
End Type


Public Type Type_ICEM_Subline_23
    
    Divide() As Double
    Num_Divide As Double
    
    Span() As Double
    Num_Span As Double
    
    Spline_Tran_z_Point() As Object
    Spline_Tran_Tip_Point() As Object
    
    Spline_Tran_x() As Object
    Spline_Tran_y() As Object
    Spline_Tran_z() As Object
    
    Spline_Tip_Part() As Object
    
    Spline_Tran_Tip_x() As Object
    Spline_Tran_Tip_y() As Object
    Spline_Tran_Tip_z() As Object
    
    Extract_Spline_Tran_z_Point As Object
    Extract_Spline_Tran_Tip_Point As Object
    Extract_Spline_Tran_x As Object
    Extract_Spline_Tran_y As Object
    Extract_Spline_Tran_z As Object
    Extract_Spline_Tran_Tip_xyz As Object
    
End Type


'************************************************************************
'Public Function
'************************************************************************
Public Function GetBrep(BRepName As String) As String

    BRepName = Replace(BRepName, "Selection_", "")
    BRepName = Left(BRepName, InStrRev(BRepName, "));"))
    BRepName = BRepName + ");WithPermanentBody;WithoutBuildError;WithSelectingFeatureSupport;MFBRepVersion_CXR15)"
    
    GetBrep = BRepName
    
End Function


Public Function Orientation_ForPercent_ByX(Spline, DocumentObject, Extract_Cache) As Boolean
    
    Dim XYZ_Cache(2)
    
    Set DPH = DocumentObject.Part.HybridShapeFactory
    
    Set Point_1 = DPH.AddNewPointOnCurveFromPercent(Spline, 0, False)
    Set Point_2 = DPH.AddNewPointOnCurveFromPercent(Spline, 0, True)

    Extract_Cache.AddConstraintTolerant Point_1, 3, False, False, 0.1, 0.5, 0.98, 1
    Extract_Cache.SetElement 1, Point_1

    Extract_Cache.AddConstraintTolerant Point_2, 3, False, False, 0.1, 0.5, 0.98, 1
    Extract_Cache.SetElement 1, Point_2
    DocumentObject.Part.Update

    Point_1.GetCoordinates XYZ_Cache
    X1 = XYZ_Cache(0)

    Point_2.GetCoordinates XYZ_Cache
    X2 = XYZ_Cache(0)

    If X1 < X2 Then
        Orientation_ForPercent_ByX = False
    Else
        Orientation_ForPercent_ByX = True
    End If

End Function


Public Function Orientation_ForPercent_ByY(Spline, DocumentObject, Extract_Cache) As Boolean
    
    Dim XYZ_Cache(2)
    
    Set DPH = DocumentObject.Part.HybridShapeFactory
    
    Set Point_1 = DPH.AddNewPointOnCurveFromPercent(Spline, 0, False)
    Set Point_2 = DPH.AddNewPointOnCurveFromPercent(Spline, 0, True)

    Extract_Cache.AddConstraintTolerant Point_1, 3, False, False, 0.1, 0.5, 0.98, 1
    Extract_Cache.SetElement 1, Point_1

    Extract_Cache.AddConstraintTolerant Point_2, 3, False, False, 0.1, 0.5, 0.98, 1
    Extract_Cache.SetElement 1, Point_2
    DocumentObject.Part.Update

    Point_1.GetCoordinates XYZ_Cache
    Y1 = XYZ_Cache(1)

    Point_2.GetCoordinates XYZ_Cache
    Y2 = XYZ_Cache(1)

    If Y1 < Y2 Then
        Orientation_ForPercent_ByY = False
    Else
        Orientation_ForPercent_ByY = True
    End If

End Function


Public Function Orientation_ForPercent_ByZ(Spline, DocumentObject, Extract_Cache) As Boolean
    
    Dim XYZ_Cache(2)
    
    Set DPH = DocumentObject.Part.HybridShapeFactory
    
    Set Point_1 = DPH.AddNewPointOnCurveFromPercent(Spline, 0, False)
    Set Point_2 = DPH.AddNewPointOnCurveFromPercent(Spline, 0, True)

    Extract_Cache.AddConstraintTolerant Point_1, 3, False, False, 0.1, 0.5, 0.98, 1
    Extract_Cache.SetElement 1, Point_1

    Extract_Cache.AddConstraintTolerant Point_2, 3, False, False, 0.1, 0.5, 0.98, 1
    Extract_Cache.SetElement 1, Point_2
    DocumentObject.Part.Update

    Point_1.GetCoordinates XYZ_Cache
    Z1 = XYZ_Cache(2)

    Point_2.GetCoordinates XYZ_Cache
    Z2 = XYZ_Cache(2)

    If Z1 < Z2 Then
        Orientation_ForPercent_ByZ = False
    Else
        Orientation_ForPercent_ByZ = True
    End If

End Function


Public Function Orientation_ForSplit_ByX(Geometry, Geometry_ToSplit, DocumentObject, Extract_Cache) As Integer
    
    Dim XYZ_Cache(2)
    
    Set DPH = DocumentObject.Part.HybridShapeFactory
    
    Set Spline_1 = DPH.AddNewHybridSplit(Geometry, Geometry_ToSplit, 1)
    Set Spline_2 = DPH.AddNewHybridSplit(Geometry, Geometry_ToSplit, -1)
    
    Set Point_1 = DPH.AddNewPointOnCurveFromPercent(Spline_1, 0.5, False)
    Set Point_2 = DPH.AddNewPointOnCurveFromPercent(Spline_2, 0.5, False)
    
    Extract_Cache.AddConstraintTolerant Point_1, 3, False, False, 0.1, 0.5, 0.98, 1
    Extract_Cache.SetElement 1, Point_1
    
    Extract_Cache.AddConstraintTolerant Point_2, 3, False, False, 0.1, 0.5, 0.98, 1
    Extract_Cache.SetElement 1, Point_2
    DocumentObject.Part.Update
    
    Point_1.GetCoordinates XYZ_Cache
    X1 = XYZ_Cache(0)

    Point_2.GetCoordinates XYZ_Cache
    X2 = XYZ_Cache(0)
    
    If X1 < X2 Then
        Orientation_ForSplit_ByX = 1
    Else
        Orientation_ForSplit_ByX = -1
    End If
    
End Function


Public Function Orientation_ForSplit_ByZ(Geometry, Geometry_ToSplit, DocumentObject, Extract_Cache) As Integer
    
    Dim XYZ_Cache(2)
    
    Set DPH = DocumentObject.Part.HybridShapeFactory
    
    Set Spline_1 = DPH.AddNewHybridSplit(Geometry, Geometry_ToSplit, 1)
    Set Spline_2 = DPH.AddNewHybridSplit(Geometry, Geometry_ToSplit, -1)
    
    Set Point_1 = DPH.AddNewPointOnCurveFromPercent(Spline_1, 0.5, False)
    Set Point_2 = DPH.AddNewPointOnCurveFromPercent(Spline_2, 0.5, False)
    
    Extract_Cache.AddConstraintTolerant Point_1, 3, False, False, 0.1, 0.5, 0.98, 1
    Extract_Cache.SetElement 1, Point_1
    
    Extract_Cache.AddConstraintTolerant Point_2, 3, False, False, 0.1, 0.5, 0.98, 1
    Extract_Cache.SetElement 1, Point_2
    DocumentObject.Part.Update
    
    Point_1.GetCoordinates XYZ_Cache
    Z1 = XYZ_Cache(2)

    Point_2.GetCoordinates XYZ_Cache
    Z2 = XYZ_Cache(2)
    
    If Z1 < Z2 Then
        Orientation_ForSplit_ByZ = 1
    Else
        Orientation_ForSplit_ByZ = -1
    End If
    
End Function
  
  
Public Function GetDistance(Point_1, Point_2, DocumentObject, Extract_Cache) As Double

    Extract_Cache.AddConstraintTolerant Point_1, 3, False, False, 0.1, 0.5, 0.98, 1
    Extract_Cache.SetElement 1, Point_1
    
    Extract_Cache.AddConstraintTolerant Point_2, 3, False, False, 0.1, 0.5, 0.98, 1
    Extract_Cache.SetElement 1, Point_2
    DocumentObject.Part.Update

    Set M = DocumentObject.GetWorkbench("SPAWorkbench").GetMeasurable(Point_1)
    GetDistance = M.GetMinimumDistance(Point_2)
        
End Function


Public Function GetAngle(Line_1, Line_2, DocumentObject, Extract_Cache) As Double
    
    Extract_Cache.AddConstraintTolerant Line_1, 3, False, False, 0.1, 0.5, 0.98, 1
    Extract_Cache.SetElement 1, Line_1
    
    Extract_Cache.AddConstraintTolerant Line_2, 3, False, False, 0.1, 0.5, 0.98, 1
    Extract_Cache.SetElement 1, Line_2
    DocumentObject.Part.Update
    
    Set M = DocumentObject.GetWorkbench("SPAWorkbench").GetMeasurable(Line_1)
    GetAngle = M.GetAngleBetween(Line_2)

End Function


Public Function StringToDouble(Data_String) As Variant

    Dim Data_Array_String() As String
    Dim Data_Array_Double() As Double
    
    Data_Array_String = Split(Data_String, ";")
    
    
    Num_Array = UBound(Data_Array_String) - LBound(Data_Array_String) + 1
    
    ReDim Data_Array_Double(1 To Num_Array) As Double
    
    For i = 1 To Num_Array
        Data_Array_Double(i) = Val(Data_Array_String(i - 1))
    Next i
    
    
    StringToDouble = Data_Array_Double
    
End Function


Function IsInArray(Data_Number, Data_Array) As Boolean
    
    Dim Element As Variant
    
    For Each Element In Data_Array
        If Data_Number = Element Then
        
            IsInArray = True
            
            Exit Function
            
        End If
    Next Element
    
    IsInArray = False
    
End Function


'************************************************************************
'Main
'************************************************************************
Sub CATMain()

    '-----------------------------------
    'StartUp
    '-----------------------------------
    Dim StartUp As StartUp
    Set StartUp = New StartUp
       
       
    Set ExcelApp = StartUp.GetExcelApp
    Set ExcelWorkbook = StartUp.GetExcelWorkbook(ExcelApp)
    
    Dim DocumentObject As Object
    Set DocumentObject = StartUp.CreatNewDocument
    

    '-----------------------------------
    'DataTrans_FromExcel
    '-----------------------------------
    Dim DataTrans_FromExcel As DataTrans_FromExcel
    Set DataTrans_FromExcel = New DataTrans_FromExcel
    
    
    'CatiaPara
    Dim SaveDir As String
    Dim Act_Debug As Integer
    Dim Act_Demo As Integer
    Dim Act_SaveStl As Integer
    Dim Act_SaveIgs As Integer
    
    DataTrans_FromExcel.CatiaPara ExcelWorkbook, _
                                  SaveDir, Act_Debug, Act_Demo, Act_SaveStl, Act_SaveIgs
           
    
    'WingPara
    Dim Num_Section As Integer
    Dim Num_PointPerSpline As Integer
    Dim Index_SurfConnect As Variant
    Dim Mode_GuideLine As Integer
    Dim MAC_Length As Double
    Dim MAC_x As Double
    
    DataTrans_FromExcel.WingPara ExcelWorkbook, _
                                 Num_Section, Num_PointPerSpline, Index_SurfConnect, Mode_GuideLine, _
                                 MAC_Length, MAC_x
    
    
    'PostPara
    Dim Mode_Post As Integer
    Dim Diameter_Fillet As Double
    Dim Rate_Fluid As Double
    Dim Rate_BOI_Fluid_MAC As Double
    Dim Rate_BOI_Fluid_Span As Double
    Dim ScaleRate As Double
    Dim Index_NonActSection_ICEM As Variant
    Dim Index_Layer2Connect_ICEM As Variant

    DataTrans_FromExcel.PostPara ExcelWorkbook, _
                                 Mode_Post, Diameter_Fillet, _
                                 Rate_Fluid, Rate_BOI_Fluid_MAC, Rate_BOI_Fluid_Span, _
                                 ScaleRate, Index_NonActSection_ICEM, Index_Layer2Connect_ICEM
    
    
    'LeadPoint
    Data_LeadPoint = DataTrans_FromExcel.LeadPoint(ExcelWorkbook, Num_Section)
    
    
    'SectionPoint
    Data_SectionPoint = DataTrans_FromExcel.SectionPoint(ExcelWorkbook, Num_Section, Num_PointPerSpline)
    
    
    If Act_Debug <> 1 Then
        On Error Resume Next
    End If
    
    If Act_Demo = 1 Then
        CATIA.RefreshDisplay = True
    Else
        CATIA.RefreshDisplay = False
    End If
    
    
    '-----------------------------------
    'Geometry_Basic
    '-----------------------------------
    Dim Geometry_Basic As Geometry_Basic
    Set Geometry_Basic = New Geometry_Basic


    'Adjust View
    Set View = CATIA.ActiveWindow.ActiveViewer
    Set ViewPoint = View.Viewpoint3D
    
    Zoom_Init = ViewPoint.Zoom
    Zoom_Local_1 = Zoom_Init / Data_SectionPoint(Num_Section * Num_PointPerSpline, 2) * 100
    
    ViewPoint.Zoom = Zoom_Local_1
    View.Update


    'DefDirection
    Dim Entity_DefDirection As Type_DefDirection
    
    Entity_DefDirection = Geometry_Basic.DefDirection(DocumentObject, Num_Section, Num_PointPerSpline, Data_SectionPoint)


    'GenGeometry
    If Mode_Post = 0 Then

        Dim Entity_GenWing As Type_GenWing

        Entity_GenWing = Geometry_Basic.GenWing(DocumentObject, _
                                                Entity_DefDirection, _
                                                Data_SectionPoint, Num_Section, Num_PointPerSpline, _
                                                Index_SurfConnect, Mode_GuideLine, _
                                                Act_Demo)

    End If

    If Mode_Post = 1 Or Mode_Post = 2 Then

        Dim Entity_GenWing_WithTrail As Type_GenWing_WithTrail

        Entity_GenWing_WithTrail = Geometry_Basic.GenWing_WithTrail(DocumentObject, _
                                                                    Entity_DefDirection, _
                                                                    Data_SectionPoint, Num_Section, Num_PointPerSpline, Diameter_Fillet, _
                                                                    Index_SurfConnect, Mode_GuideLine, _
                                                                    Act_Demo)

    End If
    
    
    '-----------------------------------
    'Geometry_SmoothAndJoint
    '-----------------------------------
    Dim Geometry_SmoothAndJoint As Geometry_SmoothAndJoint
    Set Geometry_SmoothAndJoint = New Geometry_SmoothAndJoint


    If Mode_Post = 1 Or Mode_Post = 2 Then

        Dim Entity_SmoothAndJoint As Type_SmoothAndJoint

        Entity_SmoothAndJoint = Geometry_SmoothAndJoint.SmoothAndJoint(DocumentObject, _
                                                                       Entity_GenWing_WithTrail, Entity_DefDirection, _
                                                                       Data_SectionPoint, Num_Section, Num_PointPerSpline, Diameter_Fillet, _
                                                                       Act_Demo)

    End If
        
    
    '-----------------------------------
    'Geometry_Post
    '-----------------------------------
    Dim Geometry_Post As Geometry_Post
    Set Geometry_Post = New Geometry_Post

    
    'ICEM
    If Mode_Post = 1 Then
        
        'ICEM_FluidAndBOI
        Dim Entity_ICEM_FluidAndBOI As Type_ICEM_FluidAndBOI
        
        Entity_ICEM_FluidAndBOI = Geometry_Post.ICEM_FluidAndBOI(DocumentObject, _
                                                                 Data_SectionPoint, Num_Section, Num_PointPerSpline, _
                                                                 MAC_Length, MAC_x, _
                                                                 Diameter_Fillet, Rate_Fluid, Rate_BOI_Fluid_MAC, Rate_BOI_Fluid_Span)


        'ICEM_Subline_01
        Dim Entity_ICEM_Subline_01 As Type_ICEM_Subline_01
        
        Entity_ICEM_Subline_01 = Geometry_Post.ICEM_Subline_01(DocumentObject, _
                                                               Entity_GenWing_WithTrail, Entity_SmoothAndJoint, _
                                                               Data_SectionPoint, Num_Section, Num_PointPerSpline, _
                                                               MAC_Length, MAC_x, _
                                                               Diameter_Fillet, Rate_Fluid, _
                                                               Index_NonActSection_ICEM)

        
        'Adjust View
        Set View = CATIA.ActiveWindow.ActiveViewer
        Set ViewPoint = View.Viewpoint3D
        
        Length_Chord = Sqr((Data_SectionPoint(1, 1) - Data_SectionPoint(Num_PointPerSpline, 1)) ^ 2 + _
                           (Data_SectionPoint(1, 3) - Data_SectionPoint(Num_PointPerSpline, 3)) ^ 2)
        Zoom_Local_2 = Zoom_Init / (Length_Chord * Rate_Fluid) * 100
        
        ViewPoint.Zoom = Zoom_Local_2
        View.Update


        'ICEM_Subline_23
        Dim Entity_ICEM_Subline_23 As Type_ICEM_Subline_23
        
        Entity_ICEM_Subline_23 = Geometry_Post.ICEM_Subline_23(DocumentObject, _
                                                               Entity_ICEM_FluidAndBOI, _
                                                               Entity_ICEM_Subline_01, _
                                                               Data_SectionPoint, Num_Section, Num_PointPerSpline, _
                                                               MAC_Length, MAC_x, _
                                                               Diameter_Fillet, Rate_Fluid, Rate_BOI_Fluid_MAC, Rate_BOI_Fluid_Span, _
                                                               Index_NonActSection_ICEM)


        'ICEM_Subline_12
        Dim Entity_ICEM_Subline_12 As Type_ICEM_Subline_12
        
        Entity_ICEM_Subline_12 = Geometry_Post.ICEM_Subline_12(DocumentObject, _
                                                               Entity_ICEM_FluidAndBOI, _
                                                               Entity_ICEM_Subline_01, _
                                                               Entity_ICEM_Subline_23, _
                                                               Data_SectionPoint, Num_Section, Num_PointPerSpline, _
                                                               MAC_Length, MAC_x, _
                                                               Diameter_Fillet, Rate_Fluid, Rate_BOI_Fluid_MAC, Rate_BOI_Fluid_Span, _
                                                               Index_NonActSection_ICEM, Index_Layer2Connect_ICEM)

    End If


    'FluentMeshing
    If Mode_Post = 2 Then

        Geometry_Post.FluentMeshing DocumentObject, _
                                    Entity_SmoothAndJoint, _
                                    Data_SectionPoint, Data_LeadPoint, Num_Section, Num_PointPerSpline, _
                                    MAC_Length, MAC_x, _
                                    Diameter_Fillet, Rate_Fluid, Rate_BOI_Fluid_MAC, Rate_BOI_Fluid_Span

    End If


    '-----------------------------------
    'DataTrans_ToExcel
    '-----------------------------------
    Dim DataTrans_ToExcel As DataTrans_ToExcel
    Set DataTrans_ToExcel = New DataTrans_ToExcel
    
    
    If Mode_Post = 1 Then

        DataTrans_ToExcel.PointCoord ExcelWorkbook, DocumentObject, _
                                     Entity_ICEM_Subline_01, _
                                     Entity_ICEM_Subline_12, _
                                     Entity_ICEM_Subline_23, _
                                     Num_Section, _
                                     Index_NonActSection_ICEM

    End If


    '-----------------------------------
    'Export
    '-----------------------------------
    Dim Export As Export
    Set Export = New Export
    
    
    If Mode_Post = 0 Then

        Export.Basic DocumentObject, SaveDir, Act_SaveStl, Act_SaveIgs, Zoom_Local_1

    ElseIf Mode_Post = 1 Then

        Export.ICEM DocumentObject, SaveDir, _
                    Act_SaveStl, Act_SaveIgs, Zoom_Local_1, _
                    ScaleRate, Entity_ICEM_FluidAndBOI, Entity_ICEM_Subline_01, Entity_ICEM_Subline_12, Entity_ICEM_Subline_23

    ElseIf Mode_Post = 2 Then

        Export.FluentMeshing DocumentObject, SaveDir, Act_SaveStl, Act_SaveIgs, Zoom_Local_1

    End If


    '-----------------------------------
    'Quit
    '-----------------------------------
    ExcelApp.DisplayAlerts = False
    ExcelWorkbook.SaveAs SaveDir & ".xls"
    'ExcelApp.DisplayAlerts = True
    ExcelWorkbook.Close
    ExcelApp.Quit
    
    
    Err.Clear
    On Error GoTo 0

End Sub

Attribute VB_Name = "StartUp"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'GetExcel
'*****************************
Function GetExcelApp() As Object

    Set ExcelApp = CreateObject("Excel.Application")
    
    
    Set GetExcelApp = ExcelApp
    
End Function


Function GetExcelWorkbook(ByVal ExcelApp As Object) As Object
    
    Dim Dir_Excel As String
    Dir_Excel = Environ("Dir_Excel_ForCatiaVBA")
    
    If Len(Dir_Excel) = 0 Then
        Dir_Excel = "K:\Optimize_CRM\Catia\zCRM_0038.xls"
    End If

    Set ExcelWorkbook = ExcelApp.Workbooks.Open(Dir_Excel)
    
    
    Set GetExcelWorkbook = ExcelWorkbook
    
End Function


'*****************************
'CreatNewDocument
'*****************************
Function CreatNewDocument() As Object

    On Error Resume Next
    
    CATIA.ActiveDocument.Close
    
    CATIA.Documents.Add ("Part")
    Dim DocumentObject As Object
    Set DocumentObject = CATIA.ActiveDocument
        
    Err.Clear
    On Error GoTo 0
    
    
    Set CreatNewDocument = DocumentObject

End Function
