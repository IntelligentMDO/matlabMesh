Attribute VB_Name = "DataTrans_FromExcel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'CatiaPara
'*****************************
Function CatiaPara(ByVal ExcelWorkbook As Object, ByRef SaveDir As String)
     
    Dim Data(1, 1 To 1)
    
    For j = 1 To 1
        Data(1, j) = ExcelWorkbook.Sheets("Sheet1").Cells(1, j)
    Next j
    
    SaveDir = Data(1, 1)

End Function


'*****************************
'WingPara
'*****************************
Function WingPara(ByVal ExcelWorkbook As Object, ByRef Num_Section As Integer, ByRef Num_PointPerSpline As Integer) As Variant

    Dim Data(1, 1 To 2)
    
    For j = 1 To 2
        Data(1, j) = ExcelWorkbook.Sheets("Sheet1").Cells(2, j)
    Next j
    
    Num_Section = Data(1, 1)
    Num_PointPerSpline = Data(1, 2)

End Function


'*****************************
'Divide
'*****************************
Function Divide(ByVal ExcelWorkbook As Object, ByVal Num_PointPerSpline As Integer) As Variant
    
    Dim Data()
    ReDim Data(1 To Num_PointPerSpline)
    
    For j = 1 To Num_PointPerSpline
        Data(j) = ExcelWorkbook.Sheets("Sheet1").Cells(3, j)
    Next j
    
    
    Divide = Data
        
End Function


'*****************************
'Span
'*****************************
Function Span(ByVal ExcelWorkbook As Object, ByVal Num_Section As Integer) As Variant
    
    Dim Data()
    ReDim Data(1 To Num_Section)
    
    For j = 1 To Num_Section
        Data(j) = ExcelWorkbook.Sheets("Sheet1").Cells(4, j)
    Next j
    
    
    Span = Data
        
End Function

Attribute VB_Name = "DataTrans_ToExcel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'SectionPoint
'*****************************
Function SectionPoint(ByVal ExcelWorkbook As Object, _
                      ByRef Entity_SectionPoint As Type_SectionPoint, _
                      ByVal Num_Section As Integer, ByVal Num_PointPerSpline As Integer)

    Dim XYZ_Cache(2)
    
    
    Dim Data_Write() As Double
    
    ReDim Data_Write(1 To Num_Section * Num_PointPerSpline * 2, 1 To 3) As Double
    
    
    'Get Coord
    For nSection = 1 To Num_Section
        For nPoint = 1 To Num_PointPerSpline
            
            nRow = nRow + 1
            
            Entity_SectionPoint.Point(nSection, 2, nPoint).GetCoordinates XYZ_Cache
    
            Data_Write(nRow, 1) = XYZ_Cache(0)
            If nSection = 1 Then
                Data_Write(nRow, 2) = 0
            Else
                Data_Write(nRow, 2) = XYZ_Cache(1)
            End If
            Data_Write(nRow, 3) = XYZ_Cache(2)
    
        Next nPoint
    Next nSection
    
    For nSection = Num_Section To 1 Step -1
        For nPoint = 1 To Num_PointPerSpline
            
            nRow = nRow + 1
            
            Entity_SectionPoint.Point(nSection, 1, nPoint).GetCoordinates XYZ_Cache
    
            Data_Write(nRow, 1) = XYZ_Cache(0)
            If nSection = 1 Then
                Data_Write(nRow, 2) = 0
            Else
                Data_Write(nRow, 2) = XYZ_Cache(1)
            End If
            Data_Write(nRow, 3) = XYZ_Cache(2)
    
        Next nPoint
    Next nSection
    
    
    'Write
    Row_Init = 7 + Num_Section
    Row_End = 7 + Num_Section + Num_Section * Num_PointPerSpline * 2 - 1
    
    ExcelWorkbook.Sheets("Sheet1").Range("A" & CStr(Row_Init) & ":" & "C" & CStr(Row_End)).Value = Data_Write

End Function


'*****************************
'WingPlan
'*****************************
Function WingPlan(ByVal ExcelWorkbook As Object, _
                  ByRef Entity_WingPlan As Type_WingPlan, _
                  ByVal Num_Section As Integer, _
                  ByVal Span As Variant)

    Dim Data_Write() As Double
    
    ReDim Data_Write(1 To Num_Section, 1 To 5) As Double
    
    
    'Deal Data
    For nSection = 1 To Num_Section

        Data_Write(nSection, 1) = Span(nSection)
        Data_Write(nSection, 2) = Entity_WingPlan.Length(nSection)
        Data_Write(nSection, 3) = Entity_WingPlan.Twist(nSection)
        Data_Write(nSection, 4) = Entity_WingPlan.Sweepback(nSection)
        Data_Write(nSection, 5) = Entity_WingPlan.Dihedral(nSection)
    
    Next nSection
    
    
    'Write
    Row_Init = 6
    Row_End = 6 + Num_Section - 1
    
    ExcelWorkbook.Sheets("Sheet1").Range("A" & CStr(Row_Init) & ":" & "E" & CStr(Row_End)).Value = Data_Write

End Function

Attribute VB_Name = "GetData"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'SectionPoint
'*****************************
Function SectionPoint(ByVal DocumentObject As Object, _
                      ByVal Num_Section As Integer, ByVal Num_PointPerSpline As Integer, _
                      ByVal Divide As Variant, ByVal Span As Variant) As Type_SectionPoint
    
    'CreateOrderGeometry
    Set WorkObject = DocumentObject.Part.OrderedGeometricalSets.Add()
    DocumentObject.Part.OrderedGeometricalSets.Item(2).Name = "Export"
    
    
    Set DPH = DocumentObject.Part.HybridShapeFactory
    
    Dim EmptyObject As Object
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Create Flat
    '-----------------------------------
    Dim Flat(1 To MaxNum_Array) As Object
    
    For nSection = 1 To Num_Section
        
        If nSection = 1 Then
            Dy = 0.001
        Else
            Dy = 0
        End If
        
        Set Flat(nSection) = DPH.AddNewPlaneOffset(PLANE_ZX, Span(nSection) + Dy, False)
        
        'WorkObject.InsertHybridShape Flat(nSection)
        
    Next nSection
    
    
    '-----------------------------------
    'Create Spline
    '-----------------------------------
    Dim Spline(1 To MaxNum_Array, 1 To 2) As Object

    Set Surface_Low = DocumentObject.Part.OrderedGeometricalSets.Item("Surface").HybridShapes.Item("Surface_Low")
    Set Surface_Up = DocumentObject.Part.OrderedGeometricalSets.Item("Surface").HybridShapes.Item("Surface_Up")
    
    For nSection = 1 To Num_Section
    
        Set Spline(nSection, 1) = DPH.AddNewIntersection(Surface_Low, Flat(nSection))
        Set Spline(nSection, 2) = DPH.AddNewIntersection(Surface_Up, Flat(nSection))
        
        WorkObject.InsertHybridShape Spline(nSection, 1)
        WorkObject.InsertHybridShape Spline(nSection, 2)
        
    Next nSection
    
    
    '-----------------------------------
    'Create Point
    '-----------------------------------
    Dim Orientation(1 To MaxNum_Array, 1 To 2) As Boolean
    
    Dim Point(1 To 100, 1 To 2, 1 To MaxNum_Array) As Object
    
    
    Set Extract_Cache = DPH.AddNewExtractMulti(EmptyObject)
    WorkObject.InsertHybridShape Extract_Cache
    
    
    'Solve Orientation
    For nSection = 1 To Num_Section
    
        Orientation(nSection, 1) = Orientation_ForPercent_ByX(Spline(nSection, 1), DocumentObject, Extract_Cache)
        Orientation(nSection, 2) = Orientation_ForPercent_ByX(Spline(nSection, 2), DocumentObject, Extract_Cache)
        
    Next nSection
        
        
    'Create Point
    For nSection = 1 To Num_Section
        
        nPoint = 0
        
        For nDivide = 1 To Num_PointPerSpline
            
            nPoint = nPoint + 1
            
            Set Point(nSection, 1, nPoint) = DPH.AddNewPointOnCurveFromPercent(Spline(nSection, 1), Divide(nDivide), Orientation(nSection, 1))
            Set Point(nSection, 2, nPoint) = DPH.AddNewPointOnCurveFromPercent(Spline(nSection, 2), Divide(nDivide), Orientation(nSection, 2))
            
            'WorkObject.InsertHybridShape Point(nSection, 1, nPoint)
            'WorkObject.InsertHybridShape Point(nSection, 2, nPoint)
            
        Next nDivide
    
    Next nSection

    
    '-----------------------------------
    'Extract
    '-----------------------------------
    For nSection = 1 To Num_Section
    
        Set Extract_Point_Low = DPH.AddNewExtractMulti(EmptyObject)
        Set Extract_Point_Up = DPH.AddNewExtractMulti(EmptyObject)
        
        
        For nPoint = 1 To Num_PointPerSpline
                
            Extract_Point_Low.AddConstraintTolerant Point(nSection, 1, nPoint), 3, False, False, 0.1, 0.5, 0.98, 1
            Extract_Point_Low.SetElement 1, Point(nSection, 1, nPoint)
            
            Extract_Point_Up.AddConstraintTolerant Point(nSection, 2, nPoint), 3, False, False, 0.1, 0.5, 0.98, 1
            Extract_Point_Up.SetElement 1, Point(nSection, 2, nPoint)
                
        Next nPoint
        
        
        WorkObject.InsertHybridShape Extract_Point_Low
        WorkObject.InsertHybridShape Extract_Point_Up

        Extract_Point_Low.Name = "Point_Low_" & Str(nSection)
        Extract_Point_Up.Name = "Point_Up_" & Str(nSection)

    Next nSection
    
    
    '-----------------------------------
    'Retrun
    '-----------------------------------
    ReDim SectionPoint.Point(1 To Num_Section, 1 To 2, 1 To Num_PointPerSpline) As Object
    For nSection = 1 To Num_Section
        For nDU = 1 To 2
            For nPoint = 1 To Num_PointPerSpline
            
                Set SectionPoint.Point(nSection, nDU, nPoint) = Point(nSection, nDU, nPoint)
                
            Next nPoint
        Next nDU
    Next nSection
    

End Function


'*****************************
'WingPlan
'*****************************
Function WingPlan(ByVal DocumentObject As Object, _
                  ByRef Entity_SectionPoint As Type_SectionPoint, _
                  ByVal Num_Section As Integer, ByVal Num_PointPerSpline As Integer) As Type_WingPlan

    
    'Get WorkObject
    Set WorkObject = DocumentObject.Part.OrderedGeometricalSets.Item("Export")
    
    
    Set DPH = DocumentObject.Part.HybridShapeFactory
    
    Dim EmptyObject As Object
    Dim XYZ_Cache(2)
    
    Set Direction_X = DPH.AddNewDirectionByCoord(1, 0, 0)
    Set Direction_Y = DPH.AddNewDirectionByCoord(0, 1, 0)
    Set Direction_Z = DPH.AddNewDirectionByCoord(0, 0, 1)
    
    Set PLANE_XY = DocumentObject.Part.OriginElements.PlaneXY
    Set PLANE_YZ = DocumentObject.Part.OriginElements.PlaneYZ
    Set PLANE_ZX = DocumentObject.Part.OriginElements.PlaneZX
    
    
    '-----------------------------------
    'Get Coord
    '-----------------------------------
    Dim Coord_Lead(1 To MaxNum_Array, 1 To 3) As Double
    Dim Coord_Trail_Low(1 To MaxNum_Array, 1 To 3) As Double
    Dim Coord_Trail_Up(1 To MaxNum_Array, 1 To 3) As Double
    Dim Coord_Trail(1 To MaxNum_Array, 1 To 3) As Double
    
    For nSection = 1 To Num_Section
        
        'Coord_Lead
        Entity_SectionPoint.Point(nSection, 1, 1).GetCoordinates XYZ_Cache

        Coord_Lead(nSection, 1) = XYZ_Cache(0)
        Coord_Lead(nSection, 2) = XYZ_Cache(1)
        Coord_Lead(nSection, 3) = XYZ_Cache(2)
        
        
        'Coord_Trail
        Entity_SectionPoint.Point(nSection, 1, Num_PointPerSpline).GetCoordinates XYZ_Cache

        Coord_Trail_Low(nSection, 1) = XYZ_Cache(0)
        Coord_Trail_Low(nSection, 2) = XYZ_Cache(1)
        Coord_Trail_Low(nSection, 3) = XYZ_Cache(2)
        
        Entity_SectionPoint.Point(nSection, 2, Num_PointPerSpline).GetCoordinates XYZ_Cache

        Coord_Trail_Up(nSection, 1) = XYZ_Cache(0)
        Coord_Trail_Up(nSection, 2) = XYZ_Cache(1)
        Coord_Trail_Up(nSection, 3) = XYZ_Cache(2)
        
        Coord_Trail(nSection, 1) = (Coord_Trail_Low(nSection, 1) + Coord_Trail_Up(nSection, 1)) / 2
        Coord_Trail(nSection, 2) = (Coord_Trail_Low(nSection, 2) + Coord_Trail_Up(nSection, 2)) / 2
        Coord_Trail(nSection, 3) = (Coord_Trail_Low(nSection, 3) + Coord_Trail_Up(nSection, 3)) / 2
        
    Next nSection
    
    
    '-----------------------------------
    'Solve Length
    '-----------------------------------
    Dim Length(1 To MaxNum_Array) As Double
    
    For nSection = 1 To Num_Section
    
        Length(nSection) = Sqr((Coord_Trail(nSection, 1) - Coord_Lead(nSection, 1)) ^ 2 + (Coord_Trail(nSection, 3) - Coord_Lead(nSection, 3)) ^ 2)
    
    Next nSection
    
    
    '-----------------------------------
    'Solve Twist
    '-----------------------------------
    Dim Twist(1 To MaxNum_Array) As Double
    
    For nSection = 1 To Num_Section

        Dz = Coord_Trail(nSection, 3) - Coord_Lead(nSection, 3)
        Dx = Coord_Trail(nSection, 1) - Coord_Lead(nSection, 1)

        Twist(nSection) = -Atn(Dz / Dx) * 180 / Pi

    Next nSection
    
    
    '-----------------------------------
    'Solve Sweepback
    '-----------------------------------
    Dim Data_QuaterPoint(1 To MaxNum_Array, 1 To 3) As Double
    
    Dim Coord_Lead_Cache(1 To MaxNum_Array, 1 To 3) As Double
    Dim Sweepback(1 To MaxNum_Array) As Double
    
    
    'Solve Data_QuaterPoint
    For nSection = 1 To Num_Section
        
        Dx = Coord_Trail(nSection, 1) - Coord_Lead(nSection, 1)
        Dy = Coord_Trail(nSection, 2) - Coord_Lead(nSection, 2)
        Dz = Coord_Trail(nSection, 3) - Coord_Lead(nSection, 3)
        
        Data_QuaterPoint(nSection, 1) = Coord_Lead(nSection, 1) + Dx / 4
        Data_QuaterPoint(nSection, 2) = Coord_Lead(nSection, 2) + Dy / 4
        Data_QuaterPoint(nSection, 3) = Coord_Lead(nSection, 3) + Dz / 4
                
    Next nSection
    
    
    'Solve Sweepback
    For nSection = 1 To Num_Section
        
        Coord_Lead_Cache(nSection, 1) = Data_QuaterPoint(nSection, 1) - Length(nSection) / 4
        Coord_Lead_Cache(nSection, 2) = Data_QuaterPoint(nSection, 2)
        Coord_Lead_Cache(nSection, 3) = Data_QuaterPoint(nSection, 3)
                
    Next nSection
    
    
    Sweepback(1) = 999
    
    For nSection = 2 To Num_Section
        
        Dx = Coord_Lead_Cache(nSection, 1) - Coord_Lead_Cache(nSection - 1, 1)
        Dy = Coord_Lead_Cache(nSection, 2) - Coord_Lead_Cache(nSection - 1, 2)

        Sweepback(nSection) = Atn(Dx / Dy) * 180 / Pi

    Next nSection
    
    
    '-----------------------------------
    'Solve Dihedral
    '-----------------------------------
    Dim Dihedral(1 To MaxNum_Array) As Double
    
    Dihedral(1) = 999
    
    For nSection = 2 To Num_Section

        Dz = Data_QuaterPoint(nSection, 3) - Data_QuaterPoint(nSection - 1, 3)
        Dy = Data_QuaterPoint(nSection, 2) - Data_QuaterPoint(nSection - 1, 2)

        Dihedral(nSection) = Atn(Dz / Dy) * 180 / Pi

    Next nSection
    
    
    '-----------------------------------
    'Return
    '-----------------------------------
    ReDim WingPlan.Length(1 To Num_Section) As Double
    For nSection = 1 To Num_Section

        WingPlan.Length(nSection) = Length(nSection)
 
    Next nSection
    
    
    ReDim WingPlan.Twist(1 To Num_Section) As Double
    For nSection = 1 To Num_Section

        WingPlan.Twist(nSection) = Twist(nSection)
 
    Next nSection
    
    
    ReDim WingPlan.Sweepback(1 To Num_Section) As Double
    For nSection = 1 To Num_Section

        WingPlan.Sweepback(nSection) = Sweepback(nSection)
 
    Next nSection
    
    
    ReDim WingPlan.Dihedral(1 To Num_Section) As Double
    For nSection = 1 To Num_Section

        WingPlan.Dihedral(nSection) = Dihedral(nSection)
 
    Next nSection
    
End Function

Attribute VB_Name = "MainFun"


Public Const MaxNum_Array_Point = 3000
Public Const MaxNum_Array = 100
Public Const Pi = 3.1415926


'**********************************
'Public Type
'**********************************
Public Type Type_SectionPoint

    Point() As Object
    
End Type


Public Type Type_WingPlan

    Length() As Double
    Twist() As Double
    Sweepback() As Double
    Dihedral() As Double
    
End Type


'**********************************
'Public Function
'**********************************
Public Function Orientation_ForPercent_ByX(Spline, DocumentObject, Extract_Cache) As Boolean
    
    Dim XYZ_Cache(2)
    
    Set DPH = DocumentObject.Part.HybridShapeFactory
    
    Set Point_1 = DPH.AddNewPointOnCurveFromPercent(Spline, 0, False)
    Set Point_2 = DPH.AddNewPointOnCurveFromPercent(Spline, 0, True)

    Extract_Cache.AddConstraintTolerant Point_1, 3, False, False, 0.1, 0.5, 0.98, 1
    Extract_Cache.SetElement 1, Point_1

    Extract_Cache.AddConstraintTolerant Point_2, 3, False, False, 0.1, 0.5, 0.98, 1
    Extract_Cache.SetElement 1, Point_2
    DocumentObject.Part.Update

    Point_1.GetCoordinates XYZ_Cache
    X1 = XYZ_Cache(0)

    Point_2.GetCoordinates XYZ_Cache
    X2 = XYZ_Cache(0)

    If X1 < X2 Then
        Orientation_ForPercent_ByX = False
    Else
        Orientation_ForPercent_ByX = True
    End If

End Function


'**********************************
'Main
'**********************************
Sub CATMain()
        
    '-----------------------------------
    'StartUp
    '-----------------------------------
    Dim StartUp As StartUp
    Set StartUp = New StartUp
       
    
    Set ExcelApp = StartUp.GetExcelApp
    Set ExcelWorkbook = StartUp.GetExcelWorkbook(ExcelApp)
    
    Dim DocumentObject As Object
    Set DocumentObject = StartUp.OpenDocument
    
    
    '-----------------------------------
    'DataTrans_FromExcel
    '-----------------------------------
    Dim DataTrans_FromExcel As DataTrans_FromExcel
    Set DataTrans_FromExcel = New DataTrans_FromExcel


    'CatiaPara
    Dim SaveDir As String

    DataTrans_FromExcel.CatiaPara ExcelWorkbook, SaveDir


    'WingPara
    Dim Num_Section As Integer
    Dim Num_PointPerSpline As Integer

    DataTrans_FromExcel.WingPara ExcelWorkbook, Num_Section, Num_PointPerSpline


    'Divide
    Divide = DataTrans_FromExcel.Divide(ExcelWorkbook, Num_PointPerSpline)


    'Span
    Span = DataTrans_FromExcel.Span(ExcelWorkbook, Num_Section)


    '-----------------------------------
    'Get Data
    '-----------------------------------
    Dim GetData As GetData
    Set GetData = New GetData


    'SectionPoint
    Dim Entity_SectionPoint As Type_SectionPoint

    Entity_SectionPoint = GetData.SectionPoint(DocumentObject, _
                                               Num_Section, Num_PointPerSpline, _
                                               Divide, Span)


    'WingPlan
    Dim Entity_WingPlan As Type_WingPlan

    Entity_WingPlan = GetData.WingPlan(DocumentObject, _
                                       Entity_SectionPoint, _
                                       Num_Section, Num_PointPerSpline)


    '-----------------------------------
    'DataTrans_ToExcel
    '-----------------------------------
    Dim DataTrans_ToExcel As DataTrans_ToExcel
    Set DataTrans_ToExcel = New DataTrans_ToExcel


    DataTrans_ToExcel.SectionPoint ExcelWorkbook, _
                                 Entity_SectionPoint, _
                                 Num_Section, Num_PointPerSpline


    DataTrans_ToExcel.WingPlan ExcelWorkbook, _
                               Entity_WingPlan, _
                               Num_Section, _
                               Span
    
    
    '-----------------------------------
    'Export .CATPart
    '-----------------------------------
    SaveDir_CATPart = SaveDir & "_WithPoint.CATPart"
    
    DocumentObject.SaveAs SaveDir_CATPart
        
        
    '-----------------------------------
    'Quit
    '-----------------------------------
    ExcelApp.DisplayAlerts = False
    ExcelWorkbook.SaveAs SaveDir & ".xls"
    'ExcelApp.DisplayAlerts = True
    ExcelWorkbook.Close
    ExcelApp.Quit
        
End Sub

Attribute VB_Name = "StartUp"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False


'*****************************
'GetExcel
'*****************************
Function GetExcelApp() As Object

    Set ExcelApp = CreateObject("Excel.Application")
    
    
    Set GetExcelApp = ExcelApp
    
End Function


Function GetExcelWorkbook(ByVal ExcelApp As Object) As Object
    
    Dim Dir_Excel As String
    Dir_Excel = Environ("Dir_Excel_ForCatiaVBA")
    
    If Len(Dir_Excel) = 0 Then
        Dir_Excel = "K:\Optimize_CRM\Catia\Catia_Inverse.xls"
    End If

    Set ExcelWorkbook = ExcelApp.Workbooks.Open(Dir_Excel)
    
    
    Set GetExcelWorkbook = ExcelWorkbook
    
End Function


'*****************************
'OpenDocument
'*****************************
Function OpenDocument() As Object
    
    Dim Dir_CATPart As String
    Dir_CATPart = Environ("Dir_CATPart_ForCatiaVBA")
    
    If Len(Dir_CATPart) = 0 Then
        Dir_CATPart = "K:\Optimize_CRM\Catia\Catia_Inverse.CATPart"
    End If
    
    
    On Error Resume Next
    
    CATIA.ActiveDocument.Close
    
    Err.Clear
    On Error GoTo 0
    
    Set DocumentObject = CATIA.Documents.Open(Dir_CATPart)
    
    
    Set OpenDocument = DocumentObject

End Function
